(COMMAND "POINT" "-5.615473,-2.340613,0.000000")
(COMMAND "POINT" "-4.938233,-2.013357,0.000000")
(COMMAND "POINT" "-4.273436,-1.696124,0.000000")
(COMMAND "POINT" "-3.621082,-1.388916,0.000000")
(COMMAND "POINT" "-2.981171,-1.091731,0.000000")
(COMMAND "POINT" "-2.353703,-0.804570,0.000000")
(COMMAND "POINT" "-1.738678,-0.527432,0.000000")
(COMMAND "POINT" "-1.136096,-0.260319,0.000000")
(COMMAND "POINT" "-0.545957,-0.003229,0.000000")
(COMMAND "POINT" "0.031739,0.243838,0.000000")
(COMMAND "POINT" "0.596992,0.480880,0.000000")
(COMMAND "POINT" "1.149802,0.707899,0.000000")
(COMMAND "POINT" "1.690170,0.924893,0.000000")
(COMMAND "POINT" "2.218094,1.131865,0.000000")
(COMMAND "POINT" "2.733575,1.328812,0.000000")
(COMMAND "POINT" "3.236613,1.515735,0.000000")
(COMMAND "POINT" "3.727208,1.692635,0.000000")
(COMMAND "POINT" "4.205360,1.859511,0.000000")
(COMMAND "POINT" "4.671070,2.016364,0.000000")
(COMMAND "POINT" "5.124336,2.163192,0.000000")
(COMMAND "POINT" "5.565159,2.299997,0.000000")
(COMMAND "POINT" "5.993539,2.426778,0.000000")
(COMMAND "POINT" "6.409477,2.543536,0.000000")
(COMMAND "POINT" "6.812971,2.650269,0.000000")
(COMMAND "POINT" "7.204022,2.746979,0.000000")
(COMMAND "POINT" "7.582631,2.833665,0.000000")
(COMMAND "POINT" "7.948796,2.910327,0.000000")
(COMMAND "POINT" "8.302518,2.976966,0.000000")
(COMMAND "POINT" "8.643798,3.033581,0.000000")
(COMMAND "POINT" "8.972634,3.080172,0.000000")
(COMMAND "POINT" "9.289028,3.116739,0.000000")
(COMMAND "POINT" "9.592978,3.143282,0.000000")
(COMMAND "POINT" "9.884485,3.159802,0.000000")
(COMMAND "POINT" "10.163550,3.166298,0.000000")
(COMMAND "POINT" "10.430171,3.162770,0.000000")
(COMMAND "POINT" "10.684350,3.149219,0.000000")
(COMMAND "POINT" "10.926085,3.125643,0.000000")
(COMMAND "POINT" "11.155378,3.092044,0.000000")
(COMMAND "POINT" "11.372227,3.048422,0.000000")
(COMMAND "POINT" "11.576634,2.994775,0.000000")
(COMMAND "POINT" "11.768597,2.931105,0.000000")
(COMMAND "POINT" "11.948118,2.857411,0.000000")
(COMMAND "POINT" "12.115195,2.773693,0.000000")
(COMMAND "POINT" "12.269830,2.679951,0.000000")
(COMMAND "POINT" "12.412022,2.576186,0.000000")
(COMMAND "POINT" "12.541770,2.462397,0.000000")
(COMMAND "POINT" "12.659076,2.338584,0.000000")
(COMMAND "POINT" "12.763939,2.204747,0.000000")
(COMMAND "POINT" "12.856358,2.060887,0.000000")
(COMMAND "POINT" "12.936335,1.907003,0.000000")
(COMMAND "POINT" "13.005661,1.744768,0.000000")
(COMMAND "POINT" "13.075088,1.584220,0.000000")
(COMMAND "POINT" "13.146409,1.427031,0.000000")
(COMMAND "POINT" "13.219623,1.273201,0.000000")
(COMMAND "POINT" "13.294731,1.122731,0.000000")
(COMMAND "POINT" "13.371732,0.975621,0.000000")
(COMMAND "POINT" "13.450627,0.831870,0.000000")
(COMMAND "POINT" "13.531415,0.691479,0.000000")
(COMMAND "POINT" "13.614097,0.554447,0.000000")
(COMMAND "POINT" "13.698672,0.420775,0.000000")
(COMMAND "POINT" "13.785141,0.290462,0.000000")
(COMMAND "POINT" "13.873504,0.163508,0.000000")
(COMMAND "POINT" "13.963760,0.039915,0.000000")
(COMMAND "POINT" "14.055909,-0.080320,0.000000")
(COMMAND "POINT" "14.149952,-0.197195,0.000000")
(COMMAND "POINT" "14.245889,-0.310710,0.000000")
(COMMAND "POINT" "14.343719,-0.420866,0.000000")
(COMMAND "POINT" "14.443442,-0.527662,0.000000")
(COMMAND "POINT" "14.545059,-0.631099,0.000000")
(COMMAND "POINT" "14.648570,-0.731176,0.000000")
(COMMAND "POINT" "14.753974,-0.827894,0.000000")
(COMMAND "POINT" "14.861272,-0.921253,0.000000")
(COMMAND "POINT" "14.970463,-1.011252,0.000000")
(COMMAND "POINT" "15.081548,-1.097891,0.000000")
(COMMAND "POINT" "15.194526,-1.181171,0.000000")
(COMMAND "POINT" "15.309398,-1.261091,0.000000")
(COMMAND "POINT" "15.426163,-1.337652,0.000000")
(COMMAND "POINT" "15.544822,-1.410853,0.000000")
(COMMAND "POINT" "15.665374,-1.480695,0.000000")
(COMMAND "POINT" "15.787820,-1.547178,0.000000")
(COMMAND "POINT" "15.912160,-1.610300,0.000000")
(COMMAND "POINT" "16.038392,-1.670064,0.000000")
(COMMAND "POINT" "16.166519,-1.726468,0.000000")
(COMMAND "POINT" "16.296539,-1.779512,0.000000")
(COMMAND "POINT" "16.428452,-1.829197,0.000000")
(COMMAND "POINT" "16.562259,-1.875522,0.000000")
(COMMAND "POINT" "16.697960,-1.918488,0.000000")
(COMMAND "POINT" "16.835554,-1.958094,0.000000")
(COMMAND "POINT" "16.975042,-1.994341,0.000000")
(COMMAND "POINT" "17.116423,-2.027229,0.000000")
(COMMAND "POINT" "17.259697,-2.056756,0.000000")
(COMMAND "POINT" "17.404865,-2.082925,0.000000")
(COMMAND "POINT" "17.551927,-2.105734,0.000000")
(COMMAND "POINT" "17.700882,-2.125183,0.000000")
(COMMAND "POINT" "17.851731,-2.141273,0.000000")
(COMMAND "POINT" "18.004473,-2.154003,0.000000")
(COMMAND "POINT" "18.159109,-2.163374,0.000000")
(COMMAND "POINT" "18.315638,-2.169385,0.000000")
(COMMAND "POINT" "18.474061,-2.172037,0.000000")
(COMMAND "POINT" "18.634377,-2.171330,0.000000")
(COMMAND "POINT" "-5.120198,-1.785354,-0.017684")
(COMMAND "POINT" "-4.466432,-1.482166,-0.018374")
(COMMAND "POINT" "-3.824657,-1.188317,-0.019033")
(COMMAND "POINT" "-3.194872,-0.903805,-0.019661")
(COMMAND "POINT" "-2.577078,-0.628631,-0.020258")
(COMMAND "POINT" "-1.971274,-0.362795,-0.020824")
(COMMAND "POINT" "-1.377461,-0.106298,-0.021358")
(COMMAND "POINT" "-0.795638,0.140862,-0.021862")
(COMMAND "POINT" "-0.225806,0.378683,-0.022335")
(COMMAND "POINT" "0.332035,0.607167,-0.022777")
(COMMAND "POINT" "0.877886,0.826312,-0.023187")
(COMMAND "POINT" "1.411746,1.036120,-0.023567")
(COMMAND "POINT" "1.933615,1.236589,-0.023915")
(COMMAND "POINT" "2.443494,1.427721,-0.024233")
(COMMAND "POINT" "2.941383,1.609514,-0.024519")
(COMMAND "POINT" "3.427280,1.781969,-0.024775")
(COMMAND "POINT" "3.901188,1.945086,-0.024999")
(COMMAND "POINT" "4.363104,2.098866,-0.025193")
(COMMAND "POINT" "4.813030,2.243307,-0.025355")
(COMMAND "POINT" "5.250965,2.378410,-0.025486")
(COMMAND "POINT" "5.676910,2.504175,-0.025587")
(COMMAND "POINT" "6.090864,2.620602,-0.025656")
(COMMAND "POINT" "6.492828,2.727691,-0.025694")
(COMMAND "POINT" "6.882801,2.825442,-0.025701")
(COMMAND "POINT" "7.260784,2.913854,-0.025677")
(COMMAND "POINT" "7.626775,2.992929,-0.025622")
(COMMAND "POINT" "7.980777,3.062666,-0.025536")
(COMMAND "POINT" "8.322787,3.123065,-0.025419")
(COMMAND "POINT" "8.652807,3.174125,-0.025271")
(COMMAND "POINT" "8.970837,3.215848,-0.025092")
(COMMAND "POINT" "9.276876,3.248233,-0.024882")
(COMMAND "POINT" "9.570924,3.271279,-0.024640")
(COMMAND "POINT" "9.852982,3.284988,-0.024368")
(COMMAND "POINT" "10.123049,3.289358,-0.024065")
(COMMAND "POINT" "10.381125,3.284391,-0.023730")
(COMMAND "POINT" "10.627211,3.270085,-0.023365")
(COMMAND "POINT" "10.861307,3.246441,-0.022969")
(COMMAND "POINT" "11.083411,3.213460,-0.022541")
(COMMAND "POINT" "11.293525,3.171140,-0.022083")
(COMMAND "POINT" "11.491649,3.119482,-0.021593")
(COMMAND "POINT" "11.677782,3.058486,-0.021072")
(COMMAND "POINT" "11.851924,2.988152,-0.020521")
(COMMAND "POINT" "12.014076,2.908480,-0.019938")
(COMMAND "POINT" "12.164237,2.819470,-0.019324")
(COMMAND "POINT" "12.302408,2.721122,-0.018680")
(COMMAND "POINT" "12.428588,2.613436,-0.018004")
(COMMAND "POINT" "12.542777,2.496412,-0.017297")
(COMMAND "POINT" "12.644976,2.370050,-0.016559")
(COMMAND "POINT" "12.735184,2.234350,-0.015790")
(COMMAND "POINT" "12.813402,2.089312,-0.014990")
(COMMAND "POINT" "12.881349,1.936509,-0.014166")
(COMMAND "POINT" "12.949343,1.785387,-0.013356")
(COMMAND "POINT" "13.019105,1.637518,-0.012569")
(COMMAND "POINT" "13.090634,1.492903,-0.011803")
(COMMAND "POINT" "13.163930,1.351541,-0.011059")
(COMMAND "POINT" "13.238994,1.213434,-0.010336")
(COMMAND "POINT" "13.315825,1.078580,-0.009635")
(COMMAND "POINT" "13.394423,0.946980,-0.008956")
(COMMAND "POINT" "13.474789,0.818633,-0.008298")
(COMMAND "POINT" "13.556922,0.693540,-0.007662")
(COMMAND "POINT" "13.640822,0.571701,-0.007048")
(COMMAND "POINT" "13.726490,0.453116,-0.006455")
(COMMAND "POINT" "13.813925,0.337784,-0.005884")
(COMMAND "POINT" "13.903128,0.225707,-0.005335")
(COMMAND "POINT" "13.994098,0.116882,-0.004808")
(COMMAND "POINT" "14.086835,0.011312,-0.004302")
(COMMAND "POINT" "14.181339,-0.091005,-0.003818")
(COMMAND "POINT" "14.277611,-0.190068,-0.003355")
(COMMAND "POINT" "14.375650,-0.285877,-0.002914")
(COMMAND "POINT" "14.475456,-0.378432,-0.002495")
(COMMAND "POINT" "14.577030,-0.467734,-0.002098")
(COMMAND "POINT" "14.680371,-0.553782,-0.001722")
(COMMAND "POINT" "14.785480,-0.636576,-0.001368")
(COMMAND "POINT" "14.892356,-0.716117,-0.001035")
(COMMAND "POINT" "15.000999,-0.792404,-0.000724")
(COMMAND "POINT" "15.111409,-0.865437,-0.000435")
(COMMAND "POINT" "15.223587,-0.935217,-0.000168")
(COMMAND "POINT" "15.337532,-1.001742,0.000078")
(COMMAND "POINT" "15.453245,-1.065014,0.000302")
(COMMAND "POINT" "15.570724,-1.125032,0.000504")
(COMMAND "POINT" "15.689972,-1.181797,0.000685")
(COMMAND "POINT" "15.810986,-1.235308,0.000844")
(COMMAND "POINT" "15.933768,-1.285565,0.000981")
(COMMAND "POINT" "16.058317,-1.332568,0.001097")
(COMMAND "POINT" "16.184634,-1.376318,0.001191")
(COMMAND "POINT" "16.312717,-1.416814,0.001263")
(COMMAND "POINT" "16.442569,-1.454056,0.001314")
(COMMAND "POINT" "16.574187,-1.488044,0.001343")
(COMMAND "POINT" "16.707573,-1.518779,0.001350")
(COMMAND "POINT" "16.842726,-1.546260,0.001336")
(COMMAND "POINT" "16.979647,-1.570487,0.001300")
(COMMAND "POINT" "17.118335,-1.591461,0.001242")
(COMMAND "POINT" "17.258790,-1.609181,0.001163")
(COMMAND "POINT" "17.401012,-1.623647,0.001062")
(COMMAND "POINT" "17.545002,-1.634859,0.000939")
(COMMAND "POINT" "17.690760,-1.642818,0.000795")
(COMMAND "POINT" "17.838284,-1.647523,0.000628")
(COMMAND "POINT" "17.987576,-1.648974,0.000441")
(COMMAND "POINT" "18.138635,-1.647171,0.000231")
(COMMAND "POINT" "18.291462,-1.642115,0.000000")
(COMMAND "POINT" "-4.636854,-1.239661,-0.034082")
(COMMAND "POINT" "-4.006093,-0.959893,-0.035412")
(COMMAND "POINT" "-3.386878,-0.688795,-0.036682")
(COMMAND "POINT" "-2.779209,-0.426367,-0.037892")
(COMMAND "POINT" "-2.183087,-0.172610,-0.039042")
(COMMAND "POINT" "-1.598510,0.072477,-0.040133")
(COMMAND "POINT" "-1.025478,0.308894,-0.041164")
(COMMAND "POINT" "-0.463993,0.536640,-0.042135")
(COMMAND "POINT" "0.085946,0.755715,-0.043046")
(COMMAND "POINT" "0.624339,0.966120,-0.043897")
(COMMAND "POINT" "1.151187,1.167854,-0.044688")
(COMMAND "POINT" "1.666488,1.360918,-0.045420")
(COMMAND "POINT" "2.170244,1.545312,-0.046092")
(COMMAND "POINT" "2.662453,1.721035,-0.046704")
(COMMAND "POINT" "3.143117,1.888087,-0.047256")
(COMMAND "POINT" "3.612235,2.046470,-0.047748")
(COMMAND "POINT" "4.069806,2.196181,-0.048181")
(COMMAND "POINT" "4.515832,2.337222,-0.048553")
(COMMAND "POINT" "4.950312,2.469593,-0.048866")
(COMMAND "POINT" "5.373246,2.593293,-0.049119")
(COMMAND "POINT" "5.784634,2.708323,-0.049313")
(COMMAND "POINT" "6.184477,2.814682,-0.049446")
(COMMAND "POINT" "6.572773,2.912371,-0.049519")
(COMMAND "POINT" "6.949523,3.001389,-0.049533")
(COMMAND "POINT" "7.314728,3.081737,-0.049487")
(COMMAND "POINT" "7.668386,3.153415,-0.049381")
(COMMAND "POINT" "8.010499,3.216421,-0.049215")
(COMMAND "POINT" "8.341065,3.270758,-0.048990")
(COMMAND "POINT" "8.660086,3.316424,-0.048704")
(COMMAND "POINT" "8.967561,3.353419,-0.048359")
(COMMAND "POINT" "9.263490,3.381744,-0.047954")
(COMMAND "POINT" "9.547873,3.401399,-0.047489")
(COMMAND "POINT" "9.820710,3.412383,-0.046964")
(COMMAND "POINT" "10.082001,3.414697,-0.046380")
(COMMAND "POINT" "10.331746,3.408340,-0.045735")
(COMMAND "POINT" "10.569945,3.393312,-0.045031")
(COMMAND "POINT" "10.796599,3.369615,-0.044267")
(COMMAND "POINT" "11.011706,3.337246,-0.043443")
(COMMAND "POINT" "11.215268,3.296208,-0.042560")
(COMMAND "POINT" "11.407283,3.246498,-0.041616")
(COMMAND "POINT" "11.587753,3.188119,-0.040613")
(COMMAND "POINT" "11.756676,3.121068,-0.039550")
(COMMAND "POINT" "11.914054,3.045348,-0.038427")
(COMMAND "POINT" "12.059886,2.960957,-0.037244")
(COMMAND "POINT" "12.194172,2.867895,-0.036001")
(COMMAND "POINT" "12.316912,2.766163,-0.034699")
(COMMAND "POINT" "12.428106,2.655761,-0.033336")
(COMMAND "POINT" "12.527754,2.536688,-0.031914")
(COMMAND "POINT" "12.615857,2.408944,-0.030432")
(COMMAND "POINT" "12.692413,2.272530,-0.028890")
(COMMAND "POINT" "12.759072,2.128923,-0.027302")
(COMMAND "POINT" "12.825726,1.986990,-0.025742")
(COMMAND "POINT" "12.894024,1.848207,-0.024224")
(COMMAND "POINT" "12.963967,1.712574,-0.022747")
(COMMAND "POINT" "13.035553,1.580093,-0.021313")
(COMMAND "POINT" "13.108782,1.450762,-0.019920")
(COMMAND "POINT" "13.183656,1.324582,-0.018569")
(COMMAND "POINT" "13.260174,1.201553,-0.017260")
(COMMAND "POINT" "13.338335,1.081674,-0.015993")
(COMMAND "POINT" "13.418141,0.964946,-0.014767")
(COMMAND "POINT" "13.499590,0.851369,-0.013583")
(COMMAND "POINT" "13.582684,0.740942,-0.012441")
(COMMAND "POINT" "13.667421,0.633666,-0.011341")
(COMMAND "POINT" "13.753802,0.529541,-0.010282")
(COMMAND "POINT" "13.841827,0.428567,-0.009266")
(COMMAND "POINT" "13.931496,0.330743,-0.008291")
(COMMAND "POINT" "14.022809,0.236070,-0.007358")
(COMMAND "POINT" "14.115765,0.144548,-0.006466")
(COMMAND "POINT" "14.210366,0.056177,-0.005617")
(COMMAND "POINT" "14.306611,-0.029044,-0.004809")
(COMMAND "POINT" "14.404499,-0.111114,-0.004043")
(COMMAND "POINT" "14.504031,-0.190034,-0.003318")
(COMMAND "POINT" "14.605208,-0.265802,-0.002636")
(COMMAND "POINT" "14.708028,-0.338420,-0.001995")
(COMMAND "POINT" "14.812492,-0.407887,-0.001396")
(COMMAND "POINT" "14.918600,-0.474204,-0.000839")
(COMMAND "POINT" "15.026351,-0.537370,-0.000324")
(COMMAND "POINT" "15.135747,-0.597385,0.000150")
(COMMAND "POINT" "15.246787,-0.654249,0.000582")
(COMMAND "POINT" "15.359470,-0.707962,0.000972")
(COMMAND "POINT" "15.473798,-0.758525,0.001320")
(COMMAND "POINT" "15.589769,-0.805938,0.001627")
(COMMAND "POINT" "15.707384,-0.850199,0.001891")
(COMMAND "POINT" "15.826643,-0.891310,0.002114")
(COMMAND "POINT" "15.947546,-0.929270,0.002296")
(COMMAND "POINT" "16.070093,-0.964079,0.002435")
(COMMAND "POINT" "16.194284,-0.995738,0.002533")
(COMMAND "POINT" "16.320119,-1.024245,0.002588")
(COMMAND "POINT" "16.447598,-1.049603,0.002602")
(COMMAND "POINT" "16.576720,-1.071809,0.002575")
(COMMAND "POINT" "16.707487,-1.090865,0.002505")
(COMMAND "POINT" "16.839897,-1.106770,0.002394")
(COMMAND "POINT" "16.973951,-1.119524,0.002241")
(COMMAND "POINT" "17.109649,-1.129128,0.002046")
(COMMAND "POINT" "17.246991,-1.135580,0.001810")
(COMMAND "POINT" "17.385977,-1.138882,0.001531")
(COMMAND "POINT" "17.526607,-1.139034,0.001211")
(COMMAND "POINT" "17.668881,-1.136035,0.000849")
(COMMAND "POINT" "17.812799,-1.129885,0.000445")
(COMMAND "POINT" "17.958360,-1.120584,0.000000")
(COMMAND "POINT" "-4.165440,-0.703535,-0.049194")
(COMMAND "POINT" "-3.557216,-0.446536,-0.051114")
(COMMAND "POINT" "-2.960101,-0.197558,-0.052947")
(COMMAND "POINT" "-2.374095,0.043398,-0.054694")
(COMMAND "POINT" "-1.799198,0.276334,-0.056354")
(COMMAND "POINT" "-1.235410,0.501248,-0.057928")
(COMMAND "POINT" "-0.682731,0.718142,-0.059416")
(COMMAND "POINT" "-0.141161,0.927014,-0.060817")
(COMMAND "POINT" "0.389300,1.127866,-0.062133")
(COMMAND "POINT" "0.908652,1.320696,-0.063361")
(COMMAND "POINT" "1.416895,1.505505,-0.064504")
(COMMAND "POINT" "1.914029,1.682294,-0.065560")
(COMMAND "POINT" "2.400054,1.851061,-0.066529")
(COMMAND "POINT" "2.874970,2.011807,-0.067413")
(COMMAND "POINT" "3.338777,2.164532,-0.068210")
(COMMAND "POINT" "3.791476,2.309237,-0.068920")
(COMMAND "POINT" "4.233065,2.445920,-0.069545")
(COMMAND "POINT" "4.663545,2.574582,-0.070082")
(COMMAND "POINT" "5.082916,2.695223,-0.070534")
(COMMAND "POINT" "5.491178,2.807843,-0.070899")
(COMMAND "POINT" "5.888332,2.912442,-0.071178")
(COMMAND "POINT" "6.274376,3.009020,-0.071371")
(COMMAND "POINT" "6.649311,3.097576,-0.071477")
(COMMAND "POINT" "7.013137,3.178112,-0.071496")
(COMMAND "POINT" "7.365855,3.250627,-0.071430")
(COMMAND "POINT" "7.707463,3.315121,-0.071277")
(COMMAND "POINT" "8.037962,3.371593,-0.071038")
(COMMAND "POINT" "8.357353,3.420045,-0.070712")
(COMMAND "POINT" "8.665634,3.460476,-0.070300")
(COMMAND "POINT" "8.962807,3.492885,-0.069802")
(COMMAND "POINT" "9.248870,3.517274,-0.069217")
(COMMAND "POINT" "9.523824,3.533641,-0.068546")
(COMMAND "POINT" "9.787670,3.541988,-0.067789")
(COMMAND "POINT" "10.040406,3.542313,-0.066945")
(COMMAND "POINT" "10.282034,3.534618,-0.066015")
(COMMAND "POINT" "10.512552,3.518901,-0.064998")
(COMMAND "POINT" "10.731962,3.495163,-0.063896")
(COMMAND "POINT" "10.940262,3.463404,-0.062706")
(COMMAND "POINT" "11.137454,3.423625,-0.061431")
(COMMAND "POINT" "11.323536,3.375824,-0.060069")
(COMMAND "POINT" "11.498510,3.320002,-0.058621")
(COMMAND "POINT" "11.662375,3.256159,-0.057086")
(COMMAND "POINT" "11.815130,3.184295,-0.055465")
(COMMAND "POINT" "11.956777,3.104410,-0.053758")
(COMMAND "POINT" "12.087314,3.016504,-0.051964")
(COMMAND "POINT" "12.206743,2.920577,-0.050084")
(COMMAND "POINT" "12.315063,2.816629,-0.048118")
(COMMAND "POINT" "12.412273,2.704660,-0.046065")
(COMMAND "POINT" "12.498375,2.584670,-0.043926")
(COMMAND "POINT" "12.573368,2.456659,-0.041701")
(COMMAND "POINT" "12.638831,2.322010,-0.039407")
(COMMAND "POINT" "12.704238,2.189028,-0.037156")
(COMMAND "POINT" "12.771168,2.059097,-0.034965")
(COMMAND "POINT" "12.839621,1.932216,-0.032834")
(COMMAND "POINT" "12.909598,1.808386,-0.030763")
(COMMAND "POINT" "12.981098,1.687606,-0.028753")
(COMMAND "POINT" "13.054121,1.569877,-0.026803")
(COMMAND "POINT" "13.128667,1.455198,-0.024913")
(COMMAND "POINT" "13.204736,1.343569,-0.023084")
(COMMAND "POINT" "13.282329,1.234991,-0.021315")
(COMMAND "POINT" "13.361445,1.129464,-0.019606")
(COMMAND "POINT" "13.442084,1.026987,-0.017958")
(COMMAND "POINT" "13.524246,0.927560,-0.016370")
(COMMAND "POINT" "13.607932,0.831184,-0.014842")
(COMMAND "POINT" "13.693141,0.737859,-0.013374")
(COMMAND "POINT" "13.779873,0.647584,-0.011967")
(COMMAND "POINT" "13.868128,0.560359,-0.010620")
(COMMAND "POINT" "13.957906,0.476185,-0.009333")
(COMMAND "POINT" "14.049208,0.395061,-0.008107")
(COMMAND "POINT" "14.142033,0.316988,-0.006941")
(COMMAND "POINT" "14.236381,0.241965,-0.005835")
(COMMAND "POINT" "14.332252,0.169993,-0.004790")
(COMMAND "POINT" "14.429646,0.101071,-0.003805")
(COMMAND "POINT" "14.528564,0.035200,-0.002880")
(COMMAND "POINT" "14.629005,-0.027621,-0.002015")
(COMMAND "POINT" "14.730969,-0.087391,-0.001211")
(COMMAND "POINT" "14.834456,-0.144111,-0.000467")
(COMMAND "POINT" "14.939467,-0.197780,0.000216")
(COMMAND "POINT" "15.046001,-0.248399,0.000840")
(COMMAND "POINT" "15.154058,-0.295968,0.001403")
(COMMAND "POINT" "15.263638,-0.340486,0.001905")
(COMMAND "POINT" "15.374741,-0.381953,0.002348")
(COMMAND "POINT" "15.487368,-0.420370,0.002730")
(COMMAND "POINT" "15.601518,-0.455737,0.003052")
(COMMAND "POINT" "15.717191,-0.488053,0.003313")
(COMMAND "POINT" "15.834387,-0.517318,0.003515")
(COMMAND "POINT" "15.953107,-0.543533,0.003656")
(COMMAND "POINT" "16.073349,-0.566698,0.003736")
(COMMAND "POINT" "16.195115,-0.586812,0.003756")
(COMMAND "POINT" "16.318404,-0.603876,0.003716")
(COMMAND "POINT" "16.443217,-0.617889,0.003616")
(COMMAND "POINT" "16.569552,-0.628852,0.003456")
(COMMAND "POINT" "16.697411,-0.636764,0.003235")
(COMMAND "POINT" "16.826793,-0.641626,0.002953")
(COMMAND "POINT" "16.957698,-0.643437,0.002612")
(COMMAND "POINT" "17.090127,-0.642198,0.002210")
(COMMAND "POINT" "17.224078,-0.637908,0.001748")
(COMMAND "POINT" "17.359553,-0.630568,0.001226")
(COMMAND "POINT" "17.496551,-0.620177,0.000643")
(COMMAND "POINT" "17.635072,-0.606736,0.000000")
(COMMAND "POINT" "-3.705957,-0.176974,-0.063020")
(COMMAND "POINT" "-3.119801,0.057904,-0.065479")
(COMMAND "POINT" "-2.544325,0.285392,-0.067828")
(COMMAND "POINT" "-1.979529,0.505490,-0.070066")
(COMMAND "POINT" "-1.425413,0.718199,-0.072193")
(COMMAND "POINT" "-0.881976,0.923518,-0.074209")
(COMMAND "POINT" "-0.349219,1.121447,-0.076115")
(COMMAND "POINT" "0.172858,1.311986,-0.077911")
(COMMAND "POINT" "0.684256,1.495136,-0.079595")
(COMMAND "POINT" "1.184973,1.670896,-0.081169")
(COMMAND "POINT" "1.675011,1.839266,-0.082633")
(COMMAND "POINT" "2.154369,2.000246,-0.083986")
(COMMAND "POINT" "2.623047,2.153837,-0.085228")
(COMMAND "POINT" "3.081046,2.300038,-0.086360")
(COMMAND "POINT" "3.528365,2.438849,-0.087380")
(COMMAND "POINT" "3.965004,2.570270,-0.088291")
(COMMAND "POINT" "4.390963,2.694302,-0.089091")
(COMMAND "POINT" "4.806242,2.810944,-0.089780")
(COMMAND "POINT" "5.210842,2.920196,-0.090358")
(COMMAND "POINT" "5.604762,3.022058,-0.090826")
(COMMAND "POINT" "5.988002,3.116531,-0.091183")
(COMMAND "POINT" "6.360562,3.203614,-0.091430")
(COMMAND "POINT" "6.722443,3.283307,-0.091566")
(COMMAND "POINT" "7.073644,3.355610,-0.091591")
(COMMAND "POINT" "7.414165,3.420524,-0.091506")
(COMMAND "POINT" "7.744006,3.478048,-0.091310")
(COMMAND "POINT" "8.063168,3.528182,-0.091003")
(COMMAND "POINT" "8.371650,3.570926,-0.090586")
(COMMAND "POINT" "8.669452,3.606281,-0.090058")
(COMMAND "POINT" "8.956574,3.634246,-0.089420")
(COMMAND "POINT" "9.233016,3.654821,-0.088671")
(COMMAND "POINT" "9.498779,3.668006,-0.087811")
(COMMAND "POINT" "9.753862,3.673802,-0.086841")
(COMMAND "POINT" "9.998265,3.672208,-0.085760")
(COMMAND "POINT" "10.231988,3.663224,-0.084569")
(COMMAND "POINT" "10.455032,3.646851,-0.083267")
(COMMAND "POINT" "10.667396,3.623087,-0.081854")
(COMMAND "POINT" "10.869080,3.591934,-0.080330")
(COMMAND "POINT" "11.060084,3.553391,-0.078696")
(COMMAND "POINT" "11.240409,3.507459,-0.076952")
(COMMAND "POINT" "11.410054,3.454136,-0.075096")
(COMMAND "POINT" "11.569019,3.393424,-0.073131")
(COMMAND "POINT" "11.717304,3.325323,-0.071054")
(COMMAND "POINT" "11.854909,3.249831,-0.068867")
(COMMAND "POINT" "11.981835,3.166950,-0.066569")
(COMMAND "POINT" "12.098081,3.076679,-0.064161")
(COMMAND "POINT" "12.203647,2.979018,-0.061642")
(COMMAND "POINT" "12.298534,2.873967,-0.059012")
(COMMAND "POINT" "12.382740,2.761527,-0.056272")
(COMMAND "POINT" "12.456267,2.641697,-0.053421")
(COMMAND "POINT" "12.520625,2.515770,-0.050483")
(COMMAND "POINT" "12.584877,2.391503,-0.047599")
(COMMAND "POINT" "12.650535,2.270189,-0.044792")
(COMMAND "POINT" "12.717598,2.151828,-0.042062")
(COMMAND "POINT" "12.786066,2.036421,-0.039409")
(COMMAND "POINT" "12.855939,1.923966,-0.036834")
(COMMAND "POINT" "12.927218,1.814464,-0.034336")
(COMMAND "POINT" "12.999902,1.707915,-0.031915")
(COMMAND "POINT" "13.073992,1.604320,-0.029572")
(COMMAND "POINT" "13.149486,1.503677,-0.027306")
(COMMAND "POINT" "13.226386,1.405987,-0.025117")
(COMMAND "POINT" "13.304691,1.311250,-0.023005")
(COMMAND "POINT" "13.384402,1.219466,-0.020970")
(COMMAND "POINT" "13.465517,1.130636,-0.019013")
(COMMAND "POINT" "13.548038,1.044758,-0.017133")
(COMMAND "POINT" "13.631965,0.961833,-0.015330")
(COMMAND "POINT" "13.717296,0.881861,-0.013605")
(COMMAND "POINT" "13.804033,0.804843,-0.011957")
(COMMAND "POINT" "13.892175,0.730777,-0.010386")
(COMMAND "POINT" "13.981723,0.659664,-0.008892")
(COMMAND "POINT" "14.072675,0.591504,-0.007475")
(COMMAND "POINT" "14.165033,0.526298,-0.006136")
(COMMAND "POINT" "14.258796,0.464044,-0.004874")
(COMMAND "POINT" "14.353965,0.404743,-0.003689")
(COMMAND "POINT" "14.450539,0.348395,-0.002582")
(COMMAND "POINT" "14.548518,0.295001,-0.001552")
(COMMAND "POINT" "14.647902,0.244559,-0.000599")
(COMMAND "POINT" "14.748692,0.197070,0.000277")
(COMMAND "POINT" "14.850887,0.152534,0.001076")
(COMMAND "POINT" "14.954487,0.110952,0.001797")
(COMMAND "POINT" "15.059492,0.072322,0.002441")
(COMMAND "POINT" "15.165903,0.036645,0.003008")
(COMMAND "POINT" "15.273719,0.003922,0.003497")
(COMMAND "POINT" "15.382940,-0.025849,0.003910")
(COMMAND "POINT" "15.493567,-0.052667,0.004245")
(COMMAND "POINT" "15.605599,-0.076532,0.004502")
(COMMAND "POINT" "15.719036,-0.097443,0.004683")
(COMMAND "POINT" "15.833878,-0.115402,0.004786")
(COMMAND "POINT" "15.950126,-0.130408,0.004812")
(COMMAND "POINT" "16.067779,-0.142460,0.004761")
(COMMAND "POINT" "16.186837,-0.151560,0.004633")
(COMMAND "POINT" "16.307300,-0.157707,0.004427")
(COMMAND "POINT" "16.429169,-0.160900,0.004144")
(COMMAND "POINT" "16.552443,-0.161141,0.003784")
(COMMAND "POINT" "16.677123,-0.158429,0.003346")
(COMMAND "POINT" "16.803207,-0.152763,0.002831")
(COMMAND "POINT" "16.930697,-0.144145,0.002239")
(COMMAND "POINT" "17.059592,-0.132574,0.001570")
(COMMAND "POINT" "17.189893,-0.118049,0.000824")
(COMMAND "POINT" "17.321599,-0.100572,0.000000")
(COMMAND "POINT" "-3.258405,0.340021,-0.075561")
(COMMAND "POINT" "-2.693848,0.553427,-0.078509")
(COMMAND "POINT" "-2.139551,0.760057,-0.081325")
(COMMAND "POINT" "-1.595511,0.959910,-0.084008")
(COMMAND "POINT" "-1.061730,1.152986,-0.086558")
(COMMAND "POINT" "-0.538207,1.339286,-0.088976")
(COMMAND "POINT" "-0.024942,1.518809,-0.091262")
(COMMAND "POINT" "0.478065,1.691556,-0.093414")
(COMMAND "POINT" "0.970813,1.857526,-0.095434")
(COMMAND "POINT" "1.453303,2.016719,-0.097321")
(COMMAND "POINT" "1.925534,2.169136,-0.099076")
(COMMAND "POINT" "2.387508,2.314776,-0.100698")
(COMMAND "POINT" "2.839223,2.453639,-0.102187")
(COMMAND "POINT" "3.280680,2.585726,-0.103544")
(COMMAND "POINT" "3.711878,2.711037,-0.104768")
(COMMAND "POINT" "4.132818,2.829571,-0.105860")
(COMMAND "POINT" "4.543500,2.941328,-0.106819")
(COMMAND "POINT" "4.943924,3.046308,-0.107645")
(COMMAND "POINT" "5.334089,3.144512,-0.108338")
(COMMAND "POINT" "5.713997,3.235940,-0.108899")
(COMMAND "POINT" "6.083645,3.320591,-0.109328")
(COMMAND "POINT" "6.443036,3.398465,-0.109623")
(COMMAND "POINT" "6.792168,3.469563,-0.109786")
(COMMAND "POINT" "7.131042,3.533884,-0.109817")
(COMMAND "POINT" "7.459658,3.591428,-0.109715")
(COMMAND "POINT" "7.778015,3.642196,-0.109480")
(COMMAND "POINT" "8.086115,3.686187,-0.109112")
(COMMAND "POINT" "8.383955,3.723402,-0.108612")
(COMMAND "POINT" "8.671538,3.753840,-0.107979")
(COMMAND "POINT" "8.948862,3.777501,-0.107214")
(COMMAND "POINT" "9.215928,3.794386,-0.106316")
(COMMAND "POINT" "9.472736,3.804494,-0.105285")
(COMMAND "POINT" "9.719286,3.807826,-0.104122")
(COMMAND "POINT" "9.955577,3.804381,-0.102826")
(COMMAND "POINT" "10.181610,3.794160,-0.101397")
(COMMAND "POINT" "10.397384,3.777161,-0.099836")
(COMMAND "POINT" "10.602901,3.753387,-0.098142")
(COMMAND "POINT" "10.798159,3.722835,-0.096315")
(COMMAND "POINT" "10.983159,3.685507,-0.094356")
(COMMAND "POINT" "11.157900,3.641403,-0.092264")
(COMMAND "POINT" "11.322384,3.590522,-0.090040")
(COMMAND "POINT" "11.476608,3.532864,-0.087683")
(COMMAND "POINT" "11.620575,3.468430,-0.085193")
(COMMAND "POINT" "11.754284,3.397219,-0.082571")
(COMMAND "POINT" "11.877734,3.319231,-0.079816")
(COMMAND "POINT" "11.990926,3.234467,-0.076928")
(COMMAND "POINT" "12.093859,3.142927,-0.073908")
(COMMAND "POINT" "12.186534,3.044609,-0.070755")
(COMMAND "POINT" "12.268951,2.939515,-0.067469")
(COMMAND "POINT" "12.341110,2.827645,-0.064051")
(COMMAND "POINT" "12.404454,2.710202,-0.060529")
(COMMAND "POINT" "12.467645,2.594414,-0.057070")
(COMMAND "POINT" "12.532125,2.481483,-0.053705")
(COMMAND "POINT" "12.597896,2.371411,-0.050432")
(COMMAND "POINT" "12.664957,2.264197,-0.047252")
(COMMAND "POINT" "12.733308,2.159841,-0.044164")
(COMMAND "POINT" "12.802949,2.058344,-0.041169")
(COMMAND "POINT" "12.873880,1.959705,-0.038266")
(COMMAND "POINT" "12.946101,1.863924,-0.035457")
(COMMAND "POINT" "13.019612,1.771002,-0.032739")
(COMMAND "POINT" "13.094414,1.680938,-0.030115")
(COMMAND "POINT" "13.170505,1.593732,-0.027583")
(COMMAND "POINT" "13.247887,1.509385,-0.025143")
(COMMAND "POINT" "13.326558,1.427895,-0.022797")
(COMMAND "POINT" "13.406520,1.349264,-0.020543")
(COMMAND "POINT" "13.487772,1.273492,-0.018381")
(COMMAND "POINT" "13.570314,1.200577,-0.016312")
(COMMAND "POINT" "13.654146,1.130521,-0.014336")
(COMMAND "POINT" "13.739268,1.063324,-0.012452")
(COMMAND "POINT" "13.825680,0.998984,-0.010661")
(COMMAND "POINT" "13.913383,0.937503,-0.008963")
(COMMAND "POINT" "14.002375,0.878880,-0.007357")
(COMMAND "POINT" "14.092657,0.823116,-0.005844")
(COMMAND "POINT" "14.184230,0.770209,-0.004423")
(COMMAND "POINT" "14.277093,0.720161,-0.003096")
(COMMAND "POINT" "14.371245,0.672972,-0.001860")
(COMMAND "POINT" "14.466688,0.628640,-0.000718")
(COMMAND "POINT" "14.563421,0.587167,0.000332")
(COMMAND "POINT" "14.661444,0.548552,0.001290")
(COMMAND "POINT" "14.760757,0.512796,0.002155")
(COMMAND "POINT" "14.861360,0.479898,0.002927")
(COMMAND "POINT" "14.963254,0.449858,0.003606")
(COMMAND "POINT" "15.066437,0.422676,0.004193")
(COMMAND "POINT" "15.170911,0.398353,0.004688")
(COMMAND "POINT" "15.276674,0.376888,0.005089")
(COMMAND "POINT" "15.383728,0.358281,0.005398")
(COMMAND "POINT" "15.492071,0.342533,0.005615")
(COMMAND "POINT" "15.601705,0.329643,0.005739")
(COMMAND "POINT" "15.712629,0.319611,0.005770")
(COMMAND "POINT" "15.824843,0.312437,0.005708")
(COMMAND "POINT" "15.938347,0.308122,0.005554")
(COMMAND "POINT" "16.053142,0.306665,0.005308")
(COMMAND "POINT" "16.169226,0.308067,0.004968")
(COMMAND "POINT" "16.286600,0.312326,0.004536")
(COMMAND "POINT" "16.405265,0.319444,0.004012")
(COMMAND "POINT" "16.525219,0.329421,0.003395")
(COMMAND "POINT" "16.646464,0.342255,0.002685")
(COMMAND "POINT" "16.768999,0.357948,0.001883")
(COMMAND "POINT" "16.892824,0.376499,0.000988")
(COMMAND "POINT" "17.017938,0.397908,0.000000")
(COMMAND "POINT" "-2.822783,0.847450,-0.086815")
(COMMAND "POINT" "-2.279358,1.040034,-0.090203")
(COMMAND "POINT" "-1.745777,1.226436,-0.093438")
(COMMAND "POINT" "-1.222041,1.406656,-0.096521")
(COMMAND "POINT" "-0.708149,1.580695,-0.099451")
(COMMAND "POINT" "-0.204102,1.748552,-0.102229")
(COMMAND "POINT" "0.290100,1.910228,-0.104855")
(COMMAND "POINT" "0.774458,2.065722,-0.107328")
(COMMAND "POINT" "1.248972,2.215034,-0.109649")
(COMMAND "POINT" "1.713641,2.358165,-0.111817")
(COMMAND "POINT" "2.168465,2.495115,-0.113833")
(COMMAND "POINT" "2.613445,2.625883,-0.115697")
(COMMAND "POINT" "3.048581,2.750469,-0.117408")
(COMMAND "POINT" "3.473872,2.868873,-0.118967")
(COMMAND "POINT" "3.889318,2.981096,-0.120373")
(COMMAND "POINT" "4.294920,3.087138,-0.121627")
(COMMAND "POINT" "4.690677,3.186998,-0.122729")
(COMMAND "POINT" "5.076590,3.280676,-0.123678")
(COMMAND "POINT" "5.452659,3.368172,-0.124475")
(COMMAND "POINT" "5.818883,3.449488,-0.125120")
(COMMAND "POINT" "6.175262,3.524621,-0.125612")
(COMMAND "POINT" "6.521797,3.593573,-0.125951")
(COMMAND "POINT" "6.858487,3.656343,-0.126139")
(COMMAND "POINT" "7.185333,3.712932,-0.126174")
(COMMAND "POINT" "7.502334,3.763339,-0.126056")
(COMMAND "POINT" "7.809491,3.807565,-0.125786")
(COMMAND "POINT" "8.106803,3.845609,-0.125364")
(COMMAND "POINT" "8.394271,3.877471,-0.124789")
(COMMAND "POINT" "8.671894,3.903152,-0.124062")
(COMMAND "POINT" "8.939673,3.922651,-0.123183")
(COMMAND "POINT" "9.197607,3.935969,-0.122151")
(COMMAND "POINT" "9.445696,3.943105,-0.120967")
(COMMAND "POINT" "9.683941,3.944059,-0.119630")
(COMMAND "POINT" "9.912342,3.938832,-0.118141")
(COMMAND "POINT" "10.130898,3.927424,-0.116500")
(COMMAND "POINT" "10.339610,3.909833,-0.114706")
(COMMAND "POINT" "10.538477,3.886061,-0.112760")
(COMMAND "POINT" "10.727499,3.856108,-0.110661")
(COMMAND "POINT" "10.906677,3.819973,-0.108410")
(COMMAND "POINT" "11.076011,3.777656,-0.106007")
(COMMAND "POINT" "11.235500,3.729158,-0.103451")
(COMMAND "POINT" "11.385144,3.674478,-0.100743")
(COMMAND "POINT" "11.524944,3.613617,-0.097882")
(COMMAND "POINT" "11.654900,3.546574,-0.094869")
(COMMAND "POINT" "11.775011,3.473350,-0.091704")
(COMMAND "POINT" "11.885277,3.393943,-0.088386")
(COMMAND "POINT" "11.985699,3.308356,-0.084916")
(COMMAND "POINT" "12.076276,3.216586,-0.081294")
(COMMAND "POINT" "12.157009,3.118636,-0.077519")
(COMMAND "POINT" "12.227897,3.014503,-0.073592")
(COMMAND "POINT" "12.290319,2.905308,-0.069544")
(COMMAND "POINT" "12.352541,2.797760,-0.065571")
(COMMAND "POINT" "12.415940,2.692978,-0.061704")
(COMMAND "POINT" "12.480516,2.590963,-0.057944")
(COMMAND "POINT" "12.546271,2.491715,-0.054290")
(COMMAND "POINT" "12.613203,2.395233,-0.050742")
(COMMAND "POINT" "12.681313,2.301517,-0.047301")
(COMMAND "POINT" "12.750600,2.210567,-0.043966")
(COMMAND "POINT" "12.821065,2.122384,-0.040738")
(COMMAND "POINT" "12.892708,2.036967,-0.037616")
(COMMAND "POINT" "12.965528,1.954317,-0.034600")
(COMMAND "POINT" "13.039526,1.874432,-0.031691")
(COMMAND "POINT" "13.114702,1.797315,-0.028888")
(COMMAND "POINT" "13.191055,1.722963,-0.026192")
(COMMAND "POINT" "13.268586,1.651378,-0.023602")
(COMMAND "POINT" "13.347295,1.582560,-0.021119")
(COMMAND "POINT" "13.427181,1.516507,-0.018742")
(COMMAND "POINT" "13.508245,1.453221,-0.016471")
(COMMAND "POINT" "13.590487,1.392702,-0.014307")
(COMMAND "POINT" "13.673906,1.334948,-0.012249")
(COMMAND "POINT" "13.758503,1.279961,-0.010298")
(COMMAND "POINT" "13.844277,1.227741,-0.008453")
(COMMAND "POINT" "13.931230,1.178287,-0.006714")
(COMMAND "POINT" "14.019359,1.131599,-0.005082")
(COMMAND "POINT" "14.108667,1.087677,-0.003557")
(COMMAND "POINT" "14.199152,1.046522,-0.002137")
(COMMAND "POINT" "14.290815,1.008133,-0.000825")
(COMMAND "POINT" "14.383655,0.972511,0.000382")
(COMMAND "POINT" "14.477674,0.939655,0.001482")
(COMMAND "POINT" "14.572869,0.909565,0.002476")
(COMMAND "POINT" "14.669243,0.882242,0.003363")
(COMMAND "POINT" "14.766794,0.857685,0.004144")
(COMMAND "POINT" "14.865523,0.835894,0.004818")
(COMMAND "POINT" "14.965429,0.816870,0.005386")
(COMMAND "POINT" "15.066513,0.800612,0.005847")
(COMMAND "POINT" "15.168775,0.787120,0.006202")
(COMMAND "POINT" "15.272214,0.776395,0.006451")
(COMMAND "POINT" "15.376831,0.768436,0.006593")
(COMMAND "POINT" "15.482626,0.763244,0.006629")
(COMMAND "POINT" "15.589598,0.760817,0.006559")
(COMMAND "POINT" "15.697748,0.761158,0.006382")
(COMMAND "POINT" "15.807076,0.764264,0.006098")
(COMMAND "POINT" "15.917581,0.770137,0.005708")
(COMMAND "POINT" "16.029264,0.778776,0.005212")
(COMMAND "POINT" "16.142124,0.790182,0.004610")
(COMMAND "POINT" "16.256163,0.804354,0.003900")
(COMMAND "POINT" "16.371379,0.821292,0.003085")
(COMMAND "POINT" "16.487772,0.840997,0.002163")
(COMMAND "POINT" "16.605343,0.863468,0.001135")
(COMMAND "POINT" "16.724092,0.888706,0.000000")
(COMMAND "POINT" "-2.399092,1.345313,-0.096784")
(COMMAND "POINT" "-1.876329,1.517723,-0.100560")
(COMMAND "POINT" "-1.363005,1.684529,-0.104167")
(COMMAND "POINT" "-0.859119,1.845729,-0.107604")
(COMMAND "POINT" "-0.364672,2.001326,-0.110871")
(COMMAND "POINT" "0.120337,2.151317,-0.113968")
(COMMAND "POINT" "0.595907,2.295704,-0.116895")
(COMMAND "POINT" "1.062039,2.434486,-0.119652")
(COMMAND "POINT" "1.518733,2.567663,-0.122239")
(COMMAND "POINT" "1.965987,2.695235,-0.124657")
(COMMAND "POINT" "2.403804,2.817203,-0.126904")
(COMMAND "POINT" "2.832182,2.933566,-0.128982")
(COMMAND "POINT" "3.251121,3.044325,-0.130890")
(COMMAND "POINT" "3.660622,3.149478,-0.132627")
(COMMAND "POINT" "4.060685,3.249027,-0.134195")
(COMMAND "POINT" "4.451309,3.342971,-0.135593")
(COMMAND "POINT" "4.832494,3.431311,-0.136822")
(COMMAND "POINT" "5.204241,3.514046,-0.137880")
(COMMAND "POINT" "5.566550,3.591176,-0.138768")
(COMMAND "POINT" "5.919420,3.662701,-0.139487")
(COMMAND "POINT" "6.262851,3.728622,-0.140035")
(COMMAND "POINT" "6.596845,3.788938,-0.140414")
(COMMAND "POINT" "6.921399,3.843649,-0.140623")
(COMMAND "POINT" "7.236515,3.892756,-0.140662")
(COMMAND "POINT" "7.542193,3.936258,-0.140531")
(COMMAND "POINT" "7.838432,3.974155,-0.140230")
(COMMAND "POINT" "8.125233,4.006447,-0.139759")
(COMMAND "POINT" "8.402595,4.033135,-0.139119")
(COMMAND "POINT" "8.670519,4.054218,-0.138308")
(COMMAND "POINT" "8.929004,4.069696,-0.137328")
(COMMAND "POINT" "9.178051,4.079569,-0.136177")
(COMMAND "POINT" "9.417659,4.083838,-0.134857")
(COMMAND "POINT" "9.647829,4.082502,-0.133367")
(COMMAND "POINT" "9.868560,4.075562,-0.131707")
(COMMAND "POINT" "10.079853,4.063016,-0.129877")
(COMMAND "POINT" "10.281708,4.044866,-0.127877")
(COMMAND "POINT" "10.474124,4.021112,-0.125708")
(COMMAND "POINT" "10.657101,3.991752,-0.123368")
(COMMAND "POINT" "10.830640,3.956788,-0.120859")
(COMMAND "POINT" "10.994740,3.916219,-0.118179")
(COMMAND "POINT" "11.149402,3.870046,-0.115330")
(COMMAND "POINT" "11.294626,3.818267,-0.112311")
(COMMAND "POINT" "11.430411,3.760884,-0.109122")
(COMMAND "POINT" "11.556758,3.697896,-0.105763")
(COMMAND "POINT" "11.673666,3.629304,-0.102234")
(COMMAND "POINT" "11.781135,3.555107,-0.098536")
(COMMAND "POINT" "11.879166,3.475305,-0.094667")
(COMMAND "POINT" "11.967759,3.389898,-0.090628")
(COMMAND "POINT" "12.046913,3.298887,-0.086420")
(COMMAND "POINT" "12.116629,3.202271,-0.082042")
(COMMAND "POINT" "12.178219,3.101086,-0.077530")
(COMMAND "POINT" "12.239564,3.001542,-0.073100")
(COMMAND "POINT" "12.301978,2.904676,-0.068789")
(COMMAND "POINT" "12.365459,2.810486,-0.064597")
(COMMAND "POINT" "12.430008,2.718974,-0.060524")
(COMMAND "POINT" "12.495625,2.630140,-0.056569")
(COMMAND "POINT" "12.562310,2.543982,-0.052732")
(COMMAND "POINT" "12.630063,2.460501,-0.049014")
(COMMAND "POINT" "12.698884,2.379698,-0.045415")
(COMMAND "POINT" "12.768772,2.301572,-0.041935")
(COMMAND "POINT" "12.839729,2.226123,-0.038573")
(COMMAND "POINT" "12.911754,2.153351,-0.035330")
(COMMAND "POINT" "12.984847,2.083257,-0.032206")
(COMMAND "POINT" "13.059008,2.015840,-0.029200")
(COMMAND "POINT" "13.134236,1.951099,-0.026312")
(COMMAND "POINT" "13.210533,1.889036,-0.023544")
(COMMAND "POINT" "13.287898,1.829651,-0.020894")
(COMMAND "POINT" "13.366330,1.772942,-0.018363")
(COMMAND "POINT" "13.445831,1.718911,-0.015950")
(COMMAND "POINT" "13.526399,1.667556,-0.013656")
(COMMAND "POINT" "13.608036,1.618879,-0.011480")
(COMMAND "POINT" "13.690740,1.572879,-0.009424")
(COMMAND "POINT" "13.774513,1.529557,-0.007485")
(COMMAND "POINT" "13.859353,1.488911,-0.005666")
(COMMAND "POINT" "13.945262,1.450943,-0.003965")
(COMMAND "POINT" "14.032238,1.415652,-0.002383")
(COMMAND "POINT" "14.120282,1.383038,-0.000919")
(COMMAND "POINT" "14.209394,1.353101,0.000426")
(COMMAND "POINT" "14.299575,1.325841,0.001652")
(COMMAND "POINT" "14.390823,1.301259,0.002760")
(COMMAND "POINT" "14.483139,1.279354,0.003749")
(COMMAND "POINT" "14.576523,1.260126,0.004619")
(COMMAND "POINT" "14.670975,1.243575,0.005371")
(COMMAND "POINT" "14.766495,1.229701,0.006004")
(COMMAND "POINT" "14.863083,1.218505,0.006519")
(COMMAND "POINT" "14.960739,1.209985,0.006915")
(COMMAND "POINT" "15.059463,1.204143,0.007192")
(COMMAND "POINT" "15.159255,1.200978,0.007350")
(COMMAND "POINT" "15.260115,1.200490,0.007390")
(COMMAND "POINT" "15.362043,1.202680,0.007312")
(COMMAND "POINT" "15.465039,1.207546,0.007114")
(COMMAND "POINT" "15.569103,1.215090,0.006798")
(COMMAND "POINT" "15.674235,1.225311,0.006364")
(COMMAND "POINT" "15.780434,1.238209,0.005811")
(COMMAND "POINT" "15.887702,1.253785,0.005139")
(COMMAND "POINT" "15.996038,1.272037,0.004348")
(COMMAND "POINT" "16.105441,1.292967,0.003439")
(COMMAND "POINT" "16.215913,1.316574,0.002411")
(COMMAND "POINT" "16.327452,1.342858,0.001265")
(COMMAND "POINT" "16.440060,1.371819,0.000000")
(COMMAND "POINT" "-1.987332,1.833610,-0.105467")
(COMMAND "POINT" "-1.484763,1.986496,-0.109582")
(COMMAND "POINT" "-0.991234,2.134336,-0.113512")
(COMMAND "POINT" "-0.506745,2.277130,-0.117257")
(COMMAND "POINT" "-0.031297,2.414878,-0.120817")
(COMMAND "POINT" "0.435111,2.547580,-0.124192")
(COMMAND "POINT" "0.892479,2.675236,-0.127382")
(COMMAND "POINT" "1.340807,2.797846,-0.130386")
(COMMAND "POINT" "1.780095,2.915410,-0.133206")
(COMMAND "POINT" "2.210342,3.027929,-0.135840")
(COMMAND "POINT" "2.631550,3.135401,-0.138289")
(COMMAND "POINT" "3.043717,3.237827,-0.140553")
(COMMAND "POINT" "3.446844,3.335207,-0.142632")
(COMMAND "POINT" "3.840931,3.427541,-0.144526")
(COMMAND "POINT" "4.225977,3.514830,-0.146235")
(COMMAND "POINT" "4.601984,3.597072,-0.147758")
(COMMAND "POINT" "4.968950,3.674268,-0.149096")
(COMMAND "POINT" "5.326877,3.746418,-0.150250")
(COMMAND "POINT" "5.675763,3.813523,-0.151218")
(COMMAND "POINT" "6.015608,3.875581,-0.152001")
(COMMAND "POINT" "6.346414,3.932593,-0.152599")
(COMMAND "POINT" "6.668179,3.984560,-0.153011")
(COMMAND "POINT" "6.980905,4.031480,-0.153239")
(COMMAND "POINT" "7.284590,4.073355,-0.153281")
(COMMAND "POINT" "7.579235,4.110183,-0.153138")
(COMMAND "POINT" "7.864840,4.141965,-0.152811")
(COMMAND "POINT" "8.141404,4.168702,-0.152298")
(COMMAND "POINT" "8.408929,4.190392,-0.151600")
(COMMAND "POINT" "8.667413,4.207037,-0.150716")
(COMMAND "POINT" "8.916857,4.218635,-0.149648")
(COMMAND "POINT" "9.157261,4.225188,-0.148394")
(COMMAND "POINT" "9.388625,4.226694,-0.146956")
(COMMAND "POINT" "9.610949,4.223155,-0.145332")
(COMMAND "POINT" "9.824232,4.214569,-0.143523")
(COMMAND "POINT" "10.028475,4.200938,-0.141529")
(COMMAND "POINT" "10.223678,4.182261,-0.139350")
(COMMAND "POINT" "10.409841,4.158537,-0.136985")
(COMMAND "POINT" "10.586964,4.129768,-0.134436")
(COMMAND "POINT" "10.755047,4.095953,-0.131701")
(COMMAND "POINT" "10.914089,4.057091,-0.128782")
(COMMAND "POINT" "11.064091,4.013184,-0.125677")
(COMMAND "POINT" "11.205054,3.964231,-0.122387")
(COMMAND "POINT" "11.336975,3.910231,-0.118912")
(COMMAND "POINT" "11.459857,3.851186,-0.115251")
(COMMAND "POINT" "11.573699,3.787095,-0.111406")
(COMMAND "POINT" "11.678500,3.717958,-0.107376")
(COMMAND "POINT" "11.774261,3.643774,-0.103160")
(COMMAND "POINT" "11.860983,3.564545,-0.098759")
(COMMAND "POINT" "11.938663,3.480270,-0.094173")
(COMMAND "POINT" "12.007304,3.390949,-0.089402")
(COMMAND "POINT" "12.068155,3.297536,-0.084485")
(COMMAND "POINT" "12.128716,3.205760,-0.079658")
(COMMAND "POINT" "12.190239,3.116574,-0.074961")
(COMMAND "POINT" "12.252723,3.029980,-0.070392")
(COMMAND "POINT" "12.316167,2.945976,-0.065953")
(COMMAND "POINT" "12.380573,2.864562,-0.061644")
(COMMAND "POINT" "12.445940,2.785740,-0.057463")
(COMMAND "POINT" "12.512267,2.709508,-0.053412")
(COMMAND "POINT" "12.579556,2.635867,-0.049490")
(COMMAND "POINT" "12.647806,2.564817,-0.045697")
(COMMAND "POINT" "12.717017,2.496358,-0.042034")
(COMMAND "POINT" "12.787189,2.430489,-0.038500")
(COMMAND "POINT" "12.858322,2.367211,-0.035095")
(COMMAND "POINT" "12.930416,2.306524,-0.031819")
(COMMAND "POINT" "13.003471,2.248428,-0.028673")
(COMMAND "POINT" "13.077487,2.192923,-0.025656")
(COMMAND "POINT" "13.152464,2.140008,-0.022768")
(COMMAND "POINT" "13.228402,2.089684,-0.020010")
(COMMAND "POINT" "13.305301,2.041951,-0.017381")
(COMMAND "POINT" "13.383161,1.996808,-0.014881")
(COMMAND "POINT" "13.461982,1.954257,-0.012510")
(COMMAND "POINT" "13.541764,1.914296,-0.010269")
(COMMAND "POINT" "13.622507,1.876926,-0.008157")
(COMMAND "POINT" "13.704211,1.842147,-0.006174")
(COMMAND "POINT" "13.786877,1.809958,-0.004321")
(COMMAND "POINT" "13.870503,1.780361,-0.002597")
(COMMAND "POINT" "13.955090,1.753354,-0.001002")
(COMMAND "POINT" "14.040638,1.728937,0.000464")
(COMMAND "POINT" "14.127148,1.707112,0.001800")
(COMMAND "POINT" "14.214618,1.687878,0.003007")
(COMMAND "POINT" "14.303050,1.671234,0.004085")
(COMMAND "POINT" "14.392442,1.657181,0.005034")
(COMMAND "POINT" "14.482795,1.645718,0.005853")
(COMMAND "POINT" "14.574110,1.636847,0.006543")
(COMMAND "POINT" "14.666385,1.630566,0.007104")
(COMMAND "POINT" "14.759622,1.626876,0.007535")
(COMMAND "POINT" "14.853820,1.625777,0.007837")
(COMMAND "POINT" "14.948978,1.627269,0.008010")
(COMMAND "POINT" "15.045098,1.631351,0.008053")
(COMMAND "POINT" "15.142178,1.638024,0.007968")
(COMMAND "POINT" "15.240220,1.647288,0.007753")
(COMMAND "POINT" "15.339223,1.659143,0.007408")
(COMMAND "POINT" "15.439186,1.673589,0.006935")
(COMMAND "POINT" "15.540111,1.690625,0.006332")
(COMMAND "POINT" "15.641997,1.710252,0.005600")
(COMMAND "POINT" "15.744844,1.732470,0.004738")
(COMMAND "POINT" "15.848652,1.757278,0.003748")
(COMMAND "POINT" "15.953421,1.784678,0.002628")
(COMMAND "POINT" "16.059150,1.814668,0.001379")
(COMMAND "POINT" "16.165841,1.847249,0.000000")
(COMMAND "POINT" "-1.587502,2.312341,-0.112864")
(COMMAND "POINT" "-1.104658,2.446352,-0.117268")
(COMMAND "POINT" "-0.630464,2.575857,-0.121474")
(COMMAND "POINT" "-0.164920,2.700858,-0.125481")
(COMMAND "POINT" "0.291975,2.821352,-0.129291")
(COMMAND "POINT" "0.740220,2.937342,-0.132903")
(COMMAND "POINT" "1.179816,3.048826,-0.136316")
(COMMAND "POINT" "1.610762,3.155804,-0.139531")
(COMMAND "POINT" "2.033059,3.258277,-0.142548")
(COMMAND "POINT" "2.446706,3.356245,-0.145367")
(COMMAND "POINT" "2.851703,3.449708,-0.147988")
(COMMAND "POINT" "3.248051,3.538665,-0.150411")
(COMMAND "POINT" "3.635749,3.623116,-0.152636")
(COMMAND "POINT" "4.014798,3.703063,-0.154662")
(COMMAND "POINT" "4.385197,3.778503,-0.156491")
(COMMAND "POINT" "4.746946,3.849439,-0.158121")
(COMMAND "POINT" "5.100046,3.915869,-0.159553")
(COMMAND "POINT" "5.444496,3.977794,-0.160788")
(COMMAND "POINT" "5.780297,4.035213,-0.161824")
(COMMAND "POINT" "6.107448,4.088127,-0.162661")
(COMMAND "POINT" "6.425950,4.136535,-0.163301")
(COMMAND "POINT" "6.735802,4.180439,-0.163743")
(COMMAND "POINT" "7.037004,4.219836,-0.163986")
(COMMAND "POINT" "7.329557,4.254729,-0.164032")
(COMMAND "POINT" "7.613460,4.285116,-0.163879")
(COMMAND "POINT" "7.888713,4.310997,-0.163528")
(COMMAND "POINT" "8.155317,4.332373,-0.162979")
(COMMAND "POINT" "8.413272,4.349244,-0.162232")
(COMMAND "POINT" "8.662577,4.361609,-0.161287")
(COMMAND "POINT" "8.903232,4.369469,-0.160144")
(COMMAND "POINT" "9.135238,4.372824,-0.158802")
(COMMAND "POINT" "9.358594,4.371673,-0.157263")
(COMMAND "POINT" "9.573300,4.366017,-0.155525")
(COMMAND "POINT" "9.779357,4.355855,-0.153589")
(COMMAND "POINT" "9.976764,4.341188,-0.151455")
(COMMAND "POINT" "10.165522,4.322016,-0.149123")
(COMMAND "POINT" "10.345630,4.298338,-0.146593")
(COMMAND "POINT" "10.517089,4.270155,-0.143865")
(COMMAND "POINT" "10.679898,4.237466,-0.140938")
(COMMAND "POINT" "10.834057,4.200273,-0.137814")
(COMMAND "POINT" "10.979567,4.158573,-0.134491")
(COMMAND "POINT" "11.116427,4.112368,-0.130971")
(COMMAND "POINT" "11.244638,4.061658,-0.127252")
(COMMAND "POINT" "11.364199,4.006443,-0.123335")
(COMMAND "POINT" "11.475110,3.946722,-0.119220")
(COMMAND "POINT" "11.577372,3.882496,-0.114906")
(COMMAND "POINT" "11.670984,3.813764,-0.110395")
(COMMAND "POINT" "11.755947,3.740527,-0.105686")
(COMMAND "POINT" "11.832260,3.662784,-0.100778")
(COMMAND "POINT" "11.899924,3.580537,-0.095672")
(COMMAND "POINT" "11.960126,3.494660,-0.090411")
(COMMAND "POINT" "12.019997,3.410414,-0.085245")
(COMMAND "POINT" "12.080724,3.328675,-0.080218")
(COMMAND "POINT" "12.142309,3.249443,-0.075329")
(COMMAND "POINT" "12.204750,3.172718,-0.070579")
(COMMAND "POINT" "12.268048,3.098501,-0.065967")
(COMMAND "POINT" "12.332203,3.026790,-0.061493")
(COMMAND "POINT" "12.397215,2.957587,-0.057158")
(COMMAND "POINT" "12.463083,2.890891,-0.052961")
(COMMAND "POINT" "12.529809,2.826702,-0.048902")
(COMMAND "POINT" "12.597391,2.765020,-0.044982")
(COMMAND "POINT" "12.665830,2.705845,-0.041200")
(COMMAND "POINT" "12.735126,2.649178,-0.037556")
(COMMAND "POINT" "12.805279,2.595017,-0.034051")
(COMMAND "POINT" "12.876289,2.543364,-0.030684")
(COMMAND "POINT" "12.948155,2.494218,-0.027455")
(COMMAND "POINT" "13.020879,2.447579,-0.024365")
(COMMAND "POINT" "13.094459,2.403447,-0.021413")
(COMMAND "POINT" "13.168896,2.361822,-0.018600")
(COMMAND "POINT" "13.244190,2.322704,-0.015925")
(COMMAND "POINT" "13.320341,2.286094,-0.013388")
(COMMAND "POINT" "13.397348,2.251991,-0.010989")
(COMMAND "POINT" "13.475213,2.220394,-0.008729")
(COMMAND "POINT" "13.553934,2.191305,-0.006607")
(COMMAND "POINT" "13.633512,2.164723,-0.004624")
(COMMAND "POINT" "13.713947,2.140649,-0.002779")
(COMMAND "POINT" "13.795239,2.119081,-0.001072")
(COMMAND "POINT" "13.877387,2.100020,0.000497")
(COMMAND "POINT" "13.960393,2.083467,0.001927")
(COMMAND "POINT" "14.044255,2.069421,0.003218")
(COMMAND "POINT" "14.128974,2.057882,0.004372")
(COMMAND "POINT" "14.214550,2.048850,0.005387")
(COMMAND "POINT" "14.300983,2.042325,0.006263")
(COMMAND "POINT" "14.388272,2.038307,0.007002")
(COMMAND "POINT" "14.476419,2.036797,0.007602")
(COMMAND "POINT" "14.565422,2.037793,0.008063")
(COMMAND "POINT" "14.655282,2.041297,0.008387")
(COMMAND "POINT" "14.745999,2.047308,0.008572")
(COMMAND "POINT" "14.837573,2.055826,0.008618")
(COMMAND "POINT" "14.930004,2.066851,0.008527")
(COMMAND "POINT" "15.023291,2.080384,0.008296")
(COMMAND "POINT" "15.117436,2.096423,0.007928")
(COMMAND "POINT" "15.212437,2.114970,0.007421")
(COMMAND "POINT" "15.308295,2.136023,0.006776")
(COMMAND "POINT" "15.405010,2.159584,0.005993")
(COMMAND "POINT" "15.502582,2.185652,0.005071")
(COMMAND "POINT" "15.601010,2.214227,0.004011")
(COMMAND "POINT" "15.700296,2.245310,0.002812")
(COMMAND "POINT" "15.800438,2.278899,0.001475")
(COMMAND "POINT" "15.901437,2.314996,0.000000")
(COMMAND "POINT" "-1.199603,2.781506,-0.118975")
(COMMAND "POINT" "-0.736016,2.897291,-0.123617")
(COMMAND "POINT" "-0.280696,3.009093,-0.128051")
(COMMAND "POINT" "0.166358,3.116912,-0.132276")
(COMMAND "POINT" "0.605145,3.220748,-0.136292")
(COMMAND "POINT" "1.035665,3.320602,-0.140099")
(COMMAND "POINT" "1.457918,3.416472,-0.143697")
(COMMAND "POINT" "1.871905,3.508359,-0.147086")
(COMMAND "POINT" "2.277625,3.596264,-0.150267")
(COMMAND "POINT" "2.675078,3.680185,-0.153239")
(COMMAND "POINT" "3.064264,3.760124,-0.156001")
(COMMAND "POINT" "3.445184,3.836080,-0.158555")
(COMMAND "POINT" "3.817837,3.908052,-0.160901")
(COMMAND "POINT" "4.182223,3.976042,-0.163037")
(COMMAND "POINT" "4.538343,4.040049,-0.164964")
(COMMAND "POINT" "4.886195,4.100073,-0.166683")
(COMMAND "POINT" "5.225782,4.156114,-0.168193")
(COMMAND "POINT" "5.557101,4.208172,-0.169494")
(COMMAND "POINT" "5.880153,4.256247,-0.170586")
(COMMAND "POINT" "6.194939,4.300339,-0.171469")
(COMMAND "POINT" "6.501458,4.340448,-0.172143")
(COMMAND "POINT" "6.799711,4.376574,-0.172609")
(COMMAND "POINT" "7.089697,4.408717,-0.172866")
(COMMAND "POINT" "7.371416,4.436878,-0.172913")
(COMMAND "POINT" "7.644868,4.461055,-0.172752")
(COMMAND "POINT" "7.910053,4.481250,-0.172383")
(COMMAND "POINT" "8.166972,4.497461,-0.171804")
(COMMAND "POINT" "8.415624,4.509690,-0.171016")
(COMMAND "POINT" "8.656009,4.517935,-0.170020")
(COMMAND "POINT" "8.888128,4.522198,-0.168815")
(COMMAND "POINT" "9.111980,4.522478,-0.167401")
(COMMAND "POINT" "9.327565,4.518775,-0.165778")
(COMMAND "POINT" "9.534883,4.511088,-0.163946")
(COMMAND "POINT" "9.733935,4.499419,-0.161905")
(COMMAND "POINT" "9.924720,4.483767,-0.159656")
(COMMAND "POINT" "10.107238,4.464132,-0.157198")
(COMMAND "POINT" "10.281490,4.440515,-0.154531")
(COMMAND "POINT" "10.447475,4.412914,-0.151655")
(COMMAND "POINT" "10.605193,4.381330,-0.148570")
(COMMAND "POINT" "10.754644,4.345763,-0.145276")
(COMMAND "POINT" "10.895829,4.306214,-0.141773")
(COMMAND "POINT" "11.028746,4.262681,-0.138062")
(COMMAND "POINT" "11.153398,4.215165,-0.134142")
(COMMAND "POINT" "11.269782,4.163667,-0.130013")
(COMMAND "POINT" "11.377900,4.108185,-0.125675")
(COMMAND "POINT" "11.477751,4.048721,-0.121128")
(COMMAND "POINT" "11.569335,3.985274,-0.116373")
(COMMAND "POINT" "11.652652,3.917843,-0.111408")
(COMMAND "POINT" "11.727703,3.846430,-0.106235")
(COMMAND "POINT" "11.794487,3.771034,-0.100853")
(COMMAND "POINT" "11.854132,3.692456,-0.095306")
(COMMAND "POINT" "11.913405,3.615503,-0.089861")
(COMMAND "POINT" "11.973433,3.540977,-0.084562")
(COMMAND "POINT" "12.034216,3.468877,-0.079408")
(COMMAND "POINT" "12.095755,3.399203,-0.074401")
(COMMAND "POINT" "12.158050,3.331955,-0.069539")
(COMMAND "POINT" "12.221099,3.267133,-0.064823")
(COMMAND "POINT" "12.284904,3.204738,-0.060253")
(COMMAND "POINT" "12.349465,3.144769,-0.055828")
(COMMAND "POINT" "12.414781,3.087227,-0.051550")
(COMMAND "POINT" "12.480852,3.032110,-0.047417")
(COMMAND "POINT" "12.547679,2.979420,-0.043431")
(COMMAND "POINT" "12.615261,2.929156,-0.039590")
(COMMAND "POINT" "12.683598,2.881318,-0.035895")
(COMMAND "POINT" "12.752691,2.835907,-0.032345")
(COMMAND "POINT" "12.822540,2.792922,-0.028942")
(COMMAND "POINT" "12.893143,2.752363,-0.025684")
(COMMAND "POINT" "12.964503,2.714231,-0.022573")
(COMMAND "POINT" "13.036617,2.678524,-0.019607")
(COMMAND "POINT" "13.109487,2.645244,-0.016787")
(COMMAND "POINT" "13.183112,2.614391,-0.014113")
(COMMAND "POINT" "13.257493,2.585963,-0.011584")
(COMMAND "POINT" "13.332629,2.559962,-0.009202")
(COMMAND "POINT" "13.408521,2.536387,-0.006965")
(COMMAND "POINT" "13.485168,2.515238,-0.004874")
(COMMAND "POINT" "13.562570,2.496516,-0.002929")
(COMMAND "POINT" "13.640728,2.480220,-0.001130")
(COMMAND "POINT" "13.719641,2.466350,0.000523")
(COMMAND "POINT" "13.799309,2.454906,0.002031")
(COMMAND "POINT" "13.879733,2.445889,0.003393")
(COMMAND "POINT" "13.960913,2.439298,0.004608")
(COMMAND "POINT" "14.042847,2.435133,0.005678")
(COMMAND "POINT" "14.125537,2.433395,0.006603")
(COMMAND "POINT" "14.208983,2.434082,0.007381")
(COMMAND "POINT" "14.293184,2.437196,0.008013")
(COMMAND "POINT" "14.378140,2.442737,0.008500")
(COMMAND "POINT" "14.463852,2.450703,0.008841")
(COMMAND "POINT" "14.550319,2.461096,0.009036")
(COMMAND "POINT" "14.637542,2.473915,0.009085")
(COMMAND "POINT" "14.725520,2.489160,0.008988")
(COMMAND "POINT" "14.814253,2.506832,0.008746")
(COMMAND "POINT" "14.903742,2.526930,0.008357")
(COMMAND "POINT" "14.993986,2.549454,0.007823")
(COMMAND "POINT" "15.084985,2.574404,0.007143")
(COMMAND "POINT" "15.176740,2.601781,0.006317")
(COMMAND "POINT" "15.269251,2.631584,0.005345")
(COMMAND "POINT" "15.362516,2.663813,0.004228")
(COMMAND "POINT" "15.456538,2.698469,0.002964")
(COMMAND "POINT" "15.551314,2.735550,0.001555")
(COMMAND "POINT" "15.646846,2.775058,0.000000")
(COMMAND "POINT" "-0.823635,3.241105,-0.123800")
(COMMAND "POINT" "-0.378836,3.339313,-0.128631")
(COMMAND "POINT" "0.058072,3.434043,-0.133244")
(COMMAND "POINT" "0.487087,3.525294,-0.137641")
(COMMAND "POINT" "0.908211,3.613066,-0.141819")
(COMMAND "POINT" "1.321444,3.697360,-0.145781")
(COMMAND "POINT" "1.726785,3.778175,-0.149525")
(COMMAND "POINT" "2.124234,3.855512,-0.153052")
(COMMAND "POINT" "2.513792,3.929370,-0.156361")
(COMMAND "POINT" "2.895458,3.999749,-0.159454")
(COMMAND "POINT" "3.269233,4.066650,-0.162328")
(COMMAND "POINT" "3.635116,4.130072,-0.164986")
(COMMAND "POINT" "3.993107,4.190015,-0.167426")
(COMMAND "POINT" "4.343207,4.246480,-0.169649")
(COMMAND "POINT" "4.685415,4.299466,-0.171655")
(COMMAND "POINT" "5.019731,4.348973,-0.173443")
(COMMAND "POINT" "5.346156,4.395002,-0.175014")
(COMMAND "POINT" "5.664690,4.437552,-0.176368")
(COMMAND "POINT" "5.975332,4.476624,-0.177504")
(COMMAND "POINT" "6.278082,4.512217,-0.178423")
(COMMAND "POINT" "6.572940,4.544331,-0.179125")
(COMMAND "POINT" "6.859907,4.572967,-0.179609")
(COMMAND "POINT" "7.138983,4.598124,-0.179877")
(COMMAND "POINT" "7.410166,4.619802,-0.179926")
(COMMAND "POINT" "7.673459,4.638002,-0.179759")
(COMMAND "POINT" "7.928859,4.652723,-0.179374")
(COMMAND "POINT" "8.176368,4.663966,-0.178772")
(COMMAND "POINT" "8.415986,4.671730,-0.177952")
(COMMAND "POINT" "8.647711,4.676015,-0.176916")
(COMMAND "POINT" "8.871546,4.676821,-0.175661")
(COMMAND "POINT" "9.087488,4.674149,-0.174190")
(COMMAND "POINT" "9.295539,4.667999,-0.172501")
(COMMAND "POINT" "9.495699,4.658370,-0.170595")
(COMMAND "POINT" "9.687967,4.645262,-0.168472")
(COMMAND "POINT" "9.872343,4.628675,-0.166131")
(COMMAND "POINT" "10.048827,4.608610,-0.163573")
(COMMAND "POINT" "10.217420,4.585066,-0.160798")
(COMMAND "POINT" "10.378122,4.558044,-0.157805")
(COMMAND "POINT" "10.530932,4.527543,-0.154595")
(COMMAND "POINT" "10.675850,4.493563,-0.151168")
(COMMAND "POINT" "10.812877,4.456105,-0.147523")
(COMMAND "POINT" "10.942012,4.415168,-0.143662")
(COMMAND "POINT" "11.063255,4.370752,-0.139582")
(COMMAND "POINT" "11.176607,4.322858,-0.135286")
(COMMAND "POINT" "11.282067,4.271485,-0.130772")
(COMMAND "POINT" "11.379636,4.216634,-0.126041")
(COMMAND "POINT" "11.469313,4.158304,-0.121092")
(COMMAND "POINT" "11.551098,4.096495,-0.115927")
(COMMAND "POINT" "11.624992,4.031208,-0.110543")
(COMMAND "POINT" "11.690995,3.962442,-0.104943")
(COMMAND "POINT" "11.750174,3.890925,-0.099171")
(COMMAND "POINT" "11.808941,3.821029,-0.093505")
(COMMAND "POINT" "11.868365,3.753481,-0.087991")
(COMMAND "POINT" "11.928446,3.688280,-0.082629")
(COMMAND "POINT" "11.989184,3.625429,-0.077418")
(COMMAND "POINT" "12.050578,3.564925,-0.072359")
(COMMAND "POINT" "12.112629,3.506769,-0.067452")
(COMMAND "POINT" "12.175336,3.450962,-0.062696")
(COMMAND "POINT" "12.238701,3.397502,-0.058093")
(COMMAND "POINT" "12.302722,3.346391,-0.053641")
(COMMAND "POINT" "12.367400,3.297628,-0.049341")
(COMMAND "POINT" "12.432734,3.251213,-0.045192")
(COMMAND "POINT" "12.498725,3.207147,-0.041195")
(COMMAND "POINT" "12.565373,3.165428,-0.037350")
(COMMAND "POINT" "12.632678,3.126058,-0.033657")
(COMMAND "POINT" "12.700639,3.089036,-0.030116")
(COMMAND "POINT" "12.769257,3.054362,-0.026726")
(COMMAND "POINT" "12.838532,3.022036,-0.023488")
(COMMAND "POINT" "12.908464,2.992058,-0.020402")
(COMMAND "POINT" "12.979052,2.964428,-0.017468")
(COMMAND "POINT" "13.050297,2.939147,-0.014685")
(COMMAND "POINT" "13.122198,2.916214,-0.012054")
(COMMAND "POINT" "13.194757,2.895629,-0.009575")
(COMMAND "POINT" "13.267972,2.877392,-0.007247")
(COMMAND "POINT" "13.341844,2.861503,-0.005072")
(COMMAND "POINT" "13.416372,2.847963,-0.003048")
(COMMAND "POINT" "13.491557,2.836770,-0.001176")
(COMMAND "POINT" "13.567399,2.827926,0.000545")
(COMMAND "POINT" "13.643898,2.821430,0.002113")
(COMMAND "POINT" "13.721053,2.817282,0.003530")
(COMMAND "POINT" "13.798865,2.815482,0.004795")
(COMMAND "POINT" "13.877334,2.816031,0.005909")
(COMMAND "POINT" "13.956459,2.818927,0.006870")
(COMMAND "POINT" "14.036242,2.824172,0.007680")
(COMMAND "POINT" "14.116680,2.831765,0.008338")
(COMMAND "POINT" "14.197776,2.841706,0.008845")
(COMMAND "POINT" "14.279528,2.853995,0.009199")
(COMMAND "POINT" "14.361937,2.868633,0.009402")
(COMMAND "POINT" "14.445003,2.885618,0.009453")
(COMMAND "POINT" "14.528726,2.904952,0.009353")
(COMMAND "POINT" "14.613105,2.926634,0.009100")
(COMMAND "POINT" "14.698141,2.950664,0.008696")
(COMMAND "POINT" "14.783833,2.977042,0.008140")
(COMMAND "POINT" "14.870182,3.005768,0.007433")
(COMMAND "POINT" "14.957188,3.036843,0.006573")
(COMMAND "POINT" "15.044851,3.070266,0.005562")
(COMMAND "POINT" "15.133171,3.106036,0.004399")
(COMMAND "POINT" "15.222147,3.144155,0.003085")
(COMMAND "POINT" "15.311780,3.184623,0.001618")
(COMMAND "POINT" "15.402069,3.227438,0.000000")
(COMMAND "POINT" "-0.459597,3.691138,-0.127340")
(COMMAND "POINT" "-0.033118,3.772419,-0.132309")
(COMMAND "POINT" "0.385838,3.850707,-0.137054")
(COMMAND "POINT" "0.797269,3.926003,-0.141576")
(COMMAND "POINT" "1.201176,3.998306,-0.145874")
(COMMAND "POINT" "1.597558,4.067617,-0.149949")
(COMMAND "POINT" "1.986417,4.133935,-0.153800")
(COMMAND "POINT" "2.367751,4.197261,-0.157428")
(COMMAND "POINT" "2.741561,4.257595,-0.160832")
(COMMAND "POINT" "3.107847,4.314936,-0.164012")
(COMMAND "POINT" "3.466609,4.369284,-0.166969")
(COMMAND "POINT" "3.817846,4.420640,-0.169703")
(COMMAND "POINT" "4.161560,4.469004,-0.172213")
(COMMAND "POINT" "4.497749,4.514375,-0.174499")
(COMMAND "POINT" "4.826414,4.556754,-0.176562")
(COMMAND "POINT" "5.147554,4.596140,-0.178402")
(COMMAND "POINT" "5.461171,4.632534,-0.180018")
(COMMAND "POINT" "5.767263,4.665935,-0.181410")
(COMMAND "POINT" "6.065831,4.696344,-0.182579")
(COMMAND "POINT" "6.356875,4.723761,-0.183524")
(COMMAND "POINT" "6.640395,4.748185,-0.184246")
(COMMAND "POINT" "6.916391,4.769616,-0.184744")
(COMMAND "POINT" "7.184862,4.788055,-0.185019")
(COMMAND "POINT" "7.445810,4.803502,-0.185070")
(COMMAND "POINT" "7.699233,4.815956,-0.184898")
(COMMAND "POINT" "7.945131,4.825418,-0.184502")
(COMMAND "POINT" "8.183506,4.831887,-0.183883")
(COMMAND "POINT" "8.414356,4.835364,-0.183040")
(COMMAND "POINT" "8.637683,4.835848,-0.181974")
(COMMAND "POINT" "8.853485,4.833340,-0.180684")
(COMMAND "POINT" "9.061763,4.827839,-0.179170")
(COMMAND "POINT" "9.262516,4.819346,-0.177433")
(COMMAND "POINT" "9.455746,4.807860,-0.175473")
(COMMAND "POINT" "9.641451,4.793382,-0.173288")
(COMMAND "POINT" "9.819632,4.775912,-0.170881")
(COMMAND "POINT" "9.990289,4.755449,-0.168250")
(COMMAND "POINT" "10.153422,4.731993,-0.165395")
(COMMAND "POINT" "10.309031,4.705545,-0.162317")
(COMMAND "POINT" "10.457115,4.676105,-0.159015")
(COMMAND "POINT" "10.597675,4.643672,-0.155490")
(COMMAND "POINT" "10.730711,4.608247,-0.151741")
(COMMAND "POINT" "10.856223,4.569829,-0.147769")
(COMMAND "POINT" "10.974210,4.528419,-0.143573")
(COMMAND "POINT" "11.084674,4.484017,-0.139154")
(COMMAND "POINT" "11.187613,4.436621,-0.134511")
(COMMAND "POINT" "11.283028,4.386234,-0.129644")
(COMMAND "POINT" "11.370919,4.332854,-0.124554")
(COMMAND "POINT" "11.451285,4.276481,-0.119241")
(COMMAND "POINT" "11.524128,4.217116,-0.113704")
(COMMAND "POINT" "11.589446,4.154759,-0.107943")
(COMMAND "POINT" "11.648251,4.090067,-0.102007")
(COMMAND "POINT" "11.706606,4.026990,-0.096179")
(COMMAND "POINT" "11.765521,3.966186,-0.090507")
(COMMAND "POINT" "11.824998,3.907655,-0.084991")
(COMMAND "POINT" "11.885035,3.851396,-0.079631")
(COMMAND "POINT" "11.945633,3.797410,-0.074428")
(COMMAND "POINT" "12.006791,3.745697,-0.069380")
(COMMAND "POINT" "12.068511,3.696257,-0.064489")
(COMMAND "POINT" "12.130791,3.649090,-0.059754")
(COMMAND "POINT" "12.193632,3.604196,-0.055174")
(COMMAND "POINT" "12.257034,3.561574,-0.050751")
(COMMAND "POINT" "12.320996,3.521225,-0.046484")
(COMMAND "POINT" "12.385520,3.483149,-0.042373")
(COMMAND "POINT" "12.450604,3.447346,-0.038418")
(COMMAND "POINT" "12.516249,3.413816,-0.034620")
(COMMAND "POINT" "12.582454,3.382558,-0.030977")
(COMMAND "POINT" "12.649221,3.353574,-0.027490")
(COMMAND "POINT" "12.716548,3.326862,-0.024160")
(COMMAND "POINT" "12.784436,3.302423,-0.020985")
(COMMAND "POINT" "12.852885,3.280256,-0.017967")
(COMMAND "POINT" "12.921894,3.260363,-0.015105")
(COMMAND "POINT" "12.991464,3.242743,-0.012399")
(COMMAND "POINT" "13.061596,3.227395,-0.009849")
(COMMAND "POINT" "13.132287,3.214320,-0.007455")
(COMMAND "POINT" "13.203540,3.203518,-0.005217")
(COMMAND "POINT" "13.275353,3.194989,-0.003135")
(COMMAND "POINT" "13.347727,3.188732,-0.001209")
(COMMAND "POINT" "13.420662,3.184749,0.000560")
(COMMAND "POINT" "13.494158,3.183038,0.002174")
(COMMAND "POINT" "13.568215,3.183600,0.003631")
(COMMAND "POINT" "13.642832,3.186435,0.004932")
(COMMAND "POINT" "13.718010,3.191542,0.006078")
(COMMAND "POINT" "13.793749,3.198923,0.007067")
(COMMAND "POINT" "13.870048,3.208576,0.007900")
(COMMAND "POINT" "13.946908,3.220502,0.008577")
(COMMAND "POINT" "14.024330,3.234701,0.009098")
(COMMAND "POINT" "14.102311,3.251173,0.009462")
(COMMAND "POINT" "14.180854,3.269918,0.009671")
(COMMAND "POINT" "14.259958,3.290935,0.009724")
(COMMAND "POINT" "14.339622,3.314226,0.009620")
(COMMAND "POINT" "14.419847,3.339789,0.009361")
(COMMAND "POINT" "14.500632,3.367625,0.008945")
(COMMAND "POINT" "14.581979,3.397733,0.008373")
(COMMAND "POINT" "14.663886,3.430115,0.007645")
(COMMAND "POINT" "14.746354,3.464769,0.006761")
(COMMAND "POINT" "14.829383,3.501697,0.005721")
(COMMAND "POINT" "14.912973,3.540897,0.004525")
(COMMAND "POINT" "14.997123,3.582370,0.003173")
(COMMAND "POINT" "15.081834,3.626115,0.001664")
(COMMAND "POINT" "15.167106,3.672134,0.000000")
(COMMAND "POINT" "-0.107490,4.131605,-0.129593")
(COMMAND "POINT" "0.301138,4.196607,-0.134650")
(COMMAND "POINT" "0.702602,4.259085,-0.139479")
(COMMAND "POINT" "1.096902,4.319039,-0.144081")
(COMMAND "POINT" "1.484037,4.376468,-0.148456")
(COMMAND "POINT" "1.864007,4.431372,-0.152602")
(COMMAND "POINT" "2.236813,4.483752,-0.156522")
(COMMAND "POINT" "2.602455,4.533608,-0.160214")
(COMMAND "POINT" "2.960932,4.580939,-0.163678")
(COMMAND "POINT" "3.312244,4.625746,-0.166915")
(COMMAND "POINT" "3.656392,4.668029,-0.169924")
(COMMAND "POINT" "3.993376,4.707787,-0.172706")
(COMMAND "POINT" "4.323194,4.745020,-0.175261")
(COMMAND "POINT" "4.645849,4.779729,-0.177588")
(COMMAND "POINT" "4.961339,4.811914,-0.179687")
(COMMAND "POINT" "5.269664,4.841574,-0.181559")
(COMMAND "POINT" "5.570825,4.868710,-0.183204")
(COMMAND "POINT" "5.864821,4.893321,-0.184621")
(COMMAND "POINT" "6.151653,4.915408,-0.185810")
(COMMAND "POINT" "6.431320,4.934971,-0.186772")
(COMMAND "POINT" "6.703823,4.952009,-0.187507")
(COMMAND "POINT" "6.969162,4.966523,-0.188014")
(COMMAND "POINT" "7.227335,4.978512,-0.188294")
(COMMAND "POINT" "7.478345,4.987977,-0.188346")
(COMMAND "POINT" "7.722189,4.994917,-0.188170")
(COMMAND "POINT" "7.958870,4.999333,-0.187767")
(COMMAND "POINT" "8.188385,5.001224,-0.187137")
(COMMAND "POINT" "8.410737,5.000592,-0.186279")
(COMMAND "POINT" "8.625923,4.997434,-0.185194")
(COMMAND "POINT" "8.833945,4.991752,-0.183881")
(COMMAND "POINT" "9.034803,4.983546,-0.182341")
(COMMAND "POINT" "9.228496,4.972816,-0.180573")
(COMMAND "POINT" "9.415025,4.959560,-0.178578")
(COMMAND "POINT" "9.594389,4.943781,-0.176355")
(COMMAND "POINT" "9.766589,4.925477,-0.173905")
(COMMAND "POINT" "9.931624,4.904649,-0.171227")
(COMMAND "POINT" "10.089494,4.881296,-0.168322")
(COMMAND "POINT" "10.240201,4.855419,-0.165189")
(COMMAND "POINT" "10.383742,4.827017,-0.161829")
(COMMAND "POINT" "10.520119,4.796091,-0.158242")
(COMMAND "POINT" "10.649332,4.762640,-0.154427")
(COMMAND "POINT" "10.771380,4.726665,-0.150384")
(COMMAND "POINT" "10.886263,4.688166,-0.146114")
(COMMAND "POINT" "10.993982,4.647142,-0.141616")
(COMMAND "POINT" "11.094537,4.603594,-0.136891")
(COMMAND "POINT" "11.187927,4.557521,-0.131939")
(COMMAND "POINT" "11.274152,4.508924,-0.126759")
(COMMAND "POINT" "11.353213,4.457803,-0.121351")
(COMMAND "POINT" "11.425110,4.404157,-0.115716")
(COMMAND "POINT" "11.489842,4.347986,-0.109854")
(COMMAND "POINT" "11.548363,4.289882,-0.103812")
(COMMAND "POINT" "11.606398,4.233387,-0.097881")
(COMMAND "POINT" "11.664901,4.179093,-0.092109")
(COMMAND "POINT" "11.723871,4.126999,-0.086495")
(COMMAND "POINT" "11.783309,4.077105,-0.081041")
(COMMAND "POINT" "11.843214,4.029412,-0.075745")
(COMMAND "POINT" "11.903587,3.983918,-0.070608")
(COMMAND "POINT" "11.964428,3.940625,-0.065630")
(COMMAND "POINT" "12.025736,3.899532,-0.060811")
(COMMAND "POINT" "12.087511,3.860640,-0.056151")
(COMMAND "POINT" "12.149755,3.823948,-0.051649")
(COMMAND "POINT" "12.212465,3.789456,-0.047307")
(COMMAND "POINT" "12.275644,3.757164,-0.043123")
(COMMAND "POINT" "12.339290,3.727072,-0.039098")
(COMMAND "POINT" "12.403404,3.699181,-0.035232")
(COMMAND "POINT" "12.467985,3.673490,-0.031525")
(COMMAND "POINT" "12.533033,3.649999,-0.027977")
(COMMAND "POINT" "12.598550,3.628709,-0.024587")
(COMMAND "POINT" "12.664534,3.609618,-0.021357")
(COMMAND "POINT" "12.730985,3.592728,-0.018285")
(COMMAND "POINT" "12.797904,3.578039,-0.015372")
(COMMAND "POINT" "12.865291,3.565549,-0.012618")
(COMMAND "POINT" "12.933145,3.555260,-0.010023")
(COMMAND "POINT" "13.001467,3.547171,-0.007587")
(COMMAND "POINT" "13.070257,3.541282,-0.005309")
(COMMAND "POINT" "13.139514,3.537594,-0.003191")
(COMMAND "POINT" "13.209238,3.536105,-0.001231")
(COMMAND "POINT" "13.279430,3.536817,0.000570")
(COMMAND "POINT" "13.350090,3.539730,0.002212")
(COMMAND "POINT" "13.421218,3.544842,0.003695")
(COMMAND "POINT" "13.492812,3.552155,0.005020")
(COMMAND "POINT" "13.564875,3.561668,0.006185")
(COMMAND "POINT" "13.637405,3.573381,0.007192")
(COMMAND "POINT" "13.710403,3.587295,0.008040")
(COMMAND "POINT" "13.783868,3.603409,0.008729")
(COMMAND "POINT" "13.857801,3.621723,0.009259")
(COMMAND "POINT" "13.932201,3.642237,0.009630")
(COMMAND "POINT" "14.007069,3.664952,0.009842")
(COMMAND "POINT" "14.082405,3.689866,0.009896")
(COMMAND "POINT" "14.158208,3.716982,0.009790")
(COMMAND "POINT" "14.234479,3.746297,0.009526")
(COMMAND "POINT" "14.311217,3.777812,0.009103")
(COMMAND "POINT" "14.388423,3.811528,0.008521")
(COMMAND "POINT" "14.466097,3.847444,0.007780")
(COMMAND "POINT" "14.544238,3.885561,0.006881")
(COMMAND "POINT" "14.622846,3.925877,0.005822")
(COMMAND "POINT" "14.701923,3.968394,0.004605")
(COMMAND "POINT" "14.781467,4.013111,0.003229")
(COMMAND "POINT" "14.861478,4.060029,0.001694")
(COMMAND "POINT" "14.941957,4.109146,0.000000")
(COMMAND "POINT" "0.232686,4.562506,-0.130561")
(COMMAND "POINT" "0.623932,4.611879,-0.135656")
(COMMAND "POINT" "1.008366,4.659178,-0.140521")
(COMMAND "POINT" "1.385987,4.704402,-0.145157")
(COMMAND "POINT" "1.756796,4.747551,-0.149564")
(COMMAND "POINT" "2.120792,4.788626,-0.153742")
(COMMAND "POINT" "2.477975,4.827626,-0.157691")
(COMMAND "POINT" "2.828346,4.864552,-0.161410")
(COMMAND "POINT" "3.171904,4.899403,-0.164900")
(COMMAND "POINT" "3.508650,4.932180,-0.168161")
(COMMAND "POINT" "3.838583,4.962882,-0.171193")
(COMMAND "POINT" "4.161704,4.991510,-0.173996")
(COMMAND "POINT" "4.478012,5.018063,-0.176569")
(COMMAND "POINT" "4.787507,5.042541,-0.178914")
(COMMAND "POINT" "5.090190,5.064945,-0.181029")
(COMMAND "POINT" "5.386061,5.085275,-0.182915")
(COMMAND "POINT" "5.675119,5.103529,-0.184572")
(COMMAND "POINT" "5.957364,5.119710,-0.185999")
(COMMAND "POINT" "6.232797,5.133816,-0.187198")
(COMMAND "POINT" "6.501417,5.145847,-0.188167")
(COMMAND "POINT" "6.763224,5.155804,-0.188907")
(COMMAND "POINT" "7.018219,5.163686,-0.189418")
(COMMAND "POINT" "7.266402,5.169493,-0.189700")
(COMMAND "POINT" "7.507772,5.173227,-0.189752")
(COMMAND "POINT" "7.742329,5.174885,-0.189575")
(COMMAND "POINT" "7.970074,5.174469,-0.189170")
(COMMAND "POINT" "8.191006,5.171979,-0.188535")
(COMMAND "POINT" "8.405126,5.167414,-0.187670")
(COMMAND "POINT" "8.612433,5.160774,-0.186577")
(COMMAND "POINT" "8.812928,5.152060,-0.185254")
(COMMAND "POINT" "9.006610,5.141271,-0.183703")
(COMMAND "POINT" "9.193479,5.128408,-0.181922")
(COMMAND "POINT" "9.373536,5.113470,-0.179912")
(COMMAND "POINT" "9.546780,5.096458,-0.177672")
(COMMAND "POINT" "9.713212,5.077371,-0.175204")
(COMMAND "POINT" "9.872831,5.056210,-0.172506")
(COMMAND "POINT" "10.025638,5.032974,-0.169579")
(COMMAND "POINT" "10.171632,5.007663,-0.166423")
(COMMAND "POINT" "10.310814,4.980278,-0.163038")
(COMMAND "POINT" "10.443183,4.950819,-0.159423")
(COMMAND "POINT" "10.568739,4.919285,-0.155580")
(COMMAND "POINT" "10.687483,4.885676,-0.151507")
(COMMAND "POINT" "10.799414,4.849993,-0.147205")
(COMMAND "POINT" "10.904533,4.812235,-0.142674")
(COMMAND "POINT" "11.002839,4.772403,-0.137914")
(COMMAND "POINT" "11.094333,4.730496,-0.132924")
(COMMAND "POINT" "11.179014,4.686515,-0.127705")
(COMMAND "POINT" "11.256882,4.640459,-0.122257")
(COMMAND "POINT" "11.327938,4.592328,-0.116580")
(COMMAND "POINT" "11.392181,4.542123,-0.110674")
(COMMAND "POINT" "11.450511,4.490370,-0.104587")
(COMMAND "POINT" "11.508319,4.440220,-0.098612")
(COMMAND "POINT" "11.566504,4.392202,-0.092797")
(COMMAND "POINT" "11.625066,4.346314,-0.087141")
(COMMAND "POINT" "11.684006,4.302556,-0.081646")
(COMMAND "POINT" "11.743322,4.260929,-0.076311")
(COMMAND "POINT" "11.803016,4.221432,-0.071135")
(COMMAND "POINT" "11.863087,4.184066,-0.066120")
(COMMAND "POINT" "11.923535,4.148830,-0.061265")
(COMMAND "POINT" "11.984360,4.115724,-0.056570")
(COMMAND "POINT" "12.045562,4.084749,-0.052035")
(COMMAND "POINT" "12.107141,4.055905,-0.047660")
(COMMAND "POINT" "12.169098,4.029191,-0.043445")
(COMMAND "POINT" "12.231432,4.004607,-0.039390")
(COMMAND "POINT" "12.294143,3.982154,-0.035495")
(COMMAND "POINT" "12.357230,3.961831,-0.031761")
(COMMAND "POINT" "12.420696,3.943639,-0.028186")
(COMMAND "POINT" "12.484538,3.927577,-0.024771")
(COMMAND "POINT" "12.548757,3.913645,-0.021516")
(COMMAND "POINT" "12.613354,3.901844,-0.018422")
(COMMAND "POINT" "12.678327,3.892174,-0.015487")
(COMMAND "POINT" "12.743678,3.884634,-0.012712")
(COMMAND "POINT" "12.809406,3.879224,-0.010098")
(COMMAND "POINT" "12.875511,3.875945,-0.007643")
(COMMAND "POINT" "12.941994,3.874796,-0.005349")
(COMMAND "POINT" "13.008853,3.875778,-0.003214")
(COMMAND "POINT" "13.076090,3.878890,-0.001240")
(COMMAND "POINT" "13.143703,3.884133,0.000574")
(COMMAND "POINT" "13.211694,3.891506,0.002229")
(COMMAND "POINT" "13.280062,3.901010,0.003723")
(COMMAND "POINT" "13.348807,3.912644,0.005057")
(COMMAND "POINT" "13.417929,3.926408,0.006231")
(COMMAND "POINT" "13.487429,3.942303,0.007246")
(COMMAND "POINT" "13.557305,3.960328,0.008100")
(COMMAND "POINT" "13.627559,3.980484,0.008794")
(COMMAND "POINT" "13.698190,4.002770,0.009328")
(COMMAND "POINT" "13.769198,4.027187,0.009702")
(COMMAND "POINT" "13.840583,4.053734,0.009916")
(COMMAND "POINT" "13.912345,4.082412,0.009970")
(COMMAND "POINT" "13.984485,4.113220,0.009863")
(COMMAND "POINT" "14.057001,4.146158,0.009597")
(COMMAND "POINT" "14.129895,4.181227,0.009171")
(COMMAND "POINT" "14.203166,4.218427,0.008585")
(COMMAND "POINT" "14.276814,4.257756,0.007839")
(COMMAND "POINT" "14.350839,4.299217,0.006932")
(COMMAND "POINT" "14.425241,4.342807,0.005866")
(COMMAND "POINT" "14.500021,4.388529,0.004639")
(COMMAND "POINT" "14.575177,4.436380,0.003253")
(COMMAND "POINT" "14.650711,4.486362,0.001707")
(COMMAND "POINT" "14.726622,4.538475,0.000000")
(COMMAND "POINT" "0.560932,4.983841,-0.130243")
(COMMAND "POINT" "0.935264,5.018234,-0.135325")
(COMMAND "POINT" "1.303128,5.050984,-0.140179")
(COMMAND "POINT" "1.664524,5.082092,-0.144803")
(COMMAND "POINT" "2.019452,5.111556,-0.149200")
(COMMAND "POINT" "2.367911,5.139378,-0.153367")
(COMMAND "POINT" "2.709902,5.165557,-0.157306")
(COMMAND "POINT" "3.045424,5.190093,-0.161017")
(COMMAND "POINT" "3.374478,5.212986,-0.164499")
(COMMAND "POINT" "3.697064,5.234237,-0.167752")
(COMMAND "POINT" "4.013182,5.253845,-0.170776")
(COMMAND "POINT" "4.322831,5.271810,-0.173572")
(COMMAND "POINT" "4.626012,5.288132,-0.176139")
(COMMAND "POINT" "4.922724,5.302811,-0.178478")
(COMMAND "POINT" "5.212968,5.315848,-0.180588")
(COMMAND "POINT" "5.496744,5.327242,-0.182469")
(COMMAND "POINT" "5.774052,5.336993,-0.184122")
(COMMAND "POINT" "6.044891,5.345101,-0.185546")
(COMMAND "POINT" "6.309262,5.351566,-0.186742")
(COMMAND "POINT" "6.567164,5.356389,-0.187709")
(COMMAND "POINT" "6.818599,5.359569,-0.188447")
(COMMAND "POINT" "7.063564,5.361106,-0.188956")
(COMMAND "POINT" "7.302062,5.361000,-0.189237")
(COMMAND "POINT" "7.534091,5.359252,-0.189290")
(COMMAND "POINT" "7.759652,5.355860,-0.189114")
(COMMAND "POINT" "7.978744,5.350826,-0.188709")
(COMMAND "POINT" "8.191369,5.344149,-0.188075")
(COMMAND "POINT" "8.397525,5.335830,-0.187213")
(COMMAND "POINT" "8.597212,5.325867,-0.186122")
(COMMAND "POINT" "8.790431,5.314262,-0.184803")
(COMMAND "POINT" "8.977182,5.301014,-0.183255")
(COMMAND "POINT" "9.157465,5.286123,-0.181478")
(COMMAND "POINT" "9.331279,5.269589,-0.179473")
(COMMAND "POINT" "9.498625,5.251413,-0.177239")
(COMMAND "POINT" "9.659502,5.231594,-0.174777")
(COMMAND "POINT" "9.813911,5.210132,-0.172086")
(COMMAND "POINT" "9.961852,5.187027,-0.169166")
(COMMAND "POINT" "10.103325,5.162279,-0.166018")
(COMMAND "POINT" "10.238329,5.135889,-0.162641")
(COMMAND "POINT" "10.366865,5.107856,-0.159035")
(COMMAND "POINT" "10.488932,5.078180,-0.155201")
(COMMAND "POINT" "10.604532,5.046861,-0.151138")
(COMMAND "POINT" "10.713662,5.013900,-0.146846")
(COMMAND "POINT" "10.816325,4.979295,-0.142326")
(COMMAND "POINT" "10.912519,4.943048,-0.137578")
(COMMAND "POINT" "11.002245,4.905158,-0.132600")
(COMMAND "POINT" "11.085503,4.865625,-0.127394")
(COMMAND "POINT" "11.162292,4.824450,-0.121960")
(COMMAND "POINT" "11.232613,4.781632,-0.116296")
(COMMAND "POINT" "11.296465,4.737170,-0.110404")
(COMMAND "POINT" "11.354694,4.691530,-0.104332")
(COMMAND "POINT" "11.412368,4.647489,-0.098372")
(COMMAND "POINT" "11.470331,4.605512,-0.092570")
(COMMAND "POINT" "11.528583,4.565599,-0.086929")
(COMMAND "POINT" "11.587125,4.527748,-0.081447")
(COMMAND "POINT" "11.645957,4.491962,-0.076125")
(COMMAND "POINT" "11.705078,4.458238,-0.070962")
(COMMAND "POINT" "11.764488,4.426578,-0.065959")
(COMMAND "POINT" "11.824188,4.396982,-0.061116")
(COMMAND "POINT" "11.884177,4.369448,-0.056432")
(COMMAND "POINT" "11.944456,4.343979,-0.051908")
(COMMAND "POINT" "12.005024,4.320572,-0.047544")
(COMMAND "POINT" "12.065882,4.299229,-0.043339")
(COMMAND "POINT" "12.127029,4.279950,-0.039294")
(COMMAND "POINT" "12.188466,4.262734,-0.035409")
(COMMAND "POINT" "12.250192,4.247581,-0.031683")
(COMMAND "POINT" "12.312207,4.234492,-0.028117")
(COMMAND "POINT" "12.374512,4.223466,-0.024711")
(COMMAND "POINT" "12.437106,4.214503,-0.021464")
(COMMAND "POINT" "12.499990,4.207604,-0.018377")
(COMMAND "POINT" "12.563163,4.202769,-0.015449")
(COMMAND "POINT" "12.626626,4.199996,-0.012681")
(COMMAND "POINT" "12.690378,4.199288,-0.010073")
(COMMAND "POINT" "12.754420,4.200642,-0.007625")
(COMMAND "POINT" "12.818751,4.204060,-0.005336")
(COMMAND "POINT" "12.883372,4.209542,-0.003207")
(COMMAND "POINT" "12.948282,4.217087,-0.001237")
(COMMAND "POINT" "13.013481,4.226695,0.000573")
(COMMAND "POINT" "13.078970,4.238367,0.002223")
(COMMAND "POINT" "13.144748,4.252102,0.003714")
(COMMAND "POINT" "13.210816,4.267900,0.005045")
(COMMAND "POINT" "13.277173,4.285762,0.006216")
(COMMAND "POINT" "13.343820,4.305687,0.007228")
(COMMAND "POINT" "13.410756,4.327676,0.008080")
(COMMAND "POINT" "13.477982,4.351728,0.008772")
(COMMAND "POINT" "13.545497,4.377844,0.009305")
(COMMAND "POINT" "13.613301,4.406023,0.009678")
(COMMAND "POINT" "13.681395,4.436265,0.009892")
(COMMAND "POINT" "13.749779,4.468571,0.009945")
(COMMAND "POINT" "13.818452,4.502940,0.009839")
(COMMAND "POINT" "13.887414,4.539373,0.009574")
(COMMAND "POINT" "13.956666,4.577869,0.009149")
(COMMAND "POINT" "14.026207,4.618428,0.008564")
(COMMAND "POINT" "14.096038,4.661051,0.007819")
(COMMAND "POINT" "14.166158,4.705738,0.006915")
(COMMAND "POINT" "14.236567,4.752487,0.005852")
(COMMAND "POINT" "14.307266,4.801300,0.004628")
(COMMAND "POINT" "14.378255,4.852177,0.003245")
(COMMAND "POINT" "14.449533,4.905117,0.001702")
(COMMAND "POINT" "14.521100,4.960120,0.000000")
(COMMAND "POINT" "0.877246,5.395611,-0.128639")
(COMMAND "POINT" "1.235134,5.415672,-0.133659")
(COMMAND "POINT" "1.586889,5.434505,-0.138452")
(COMMAND "POINT" "1.932513,5.452109,-0.143020")
(COMMAND "POINT" "2.272005,5.468483,-0.147362")
(COMMAND "POINT" "2.605365,5.483628,-0.151479")
(COMMAND "POINT" "2.932593,5.497544,-0.155369")
(COMMAND "POINT" "3.253690,5.510231,-0.159034")
(COMMAND "POINT" "3.568654,5.521689,-0.162473")
(COMMAND "POINT" "3.877487,5.531917,-0.165686")
(COMMAND "POINT" "4.180188,5.540917,-0.168673")
(COMMAND "POINT" "4.476757,5.548687,-0.171434")
(COMMAND "POINT" "4.767194,5.555228,-0.173970")
(COMMAND "POINT" "5.051499,5.560540,-0.176280")
(COMMAND "POINT" "5.329673,5.564622,-0.178364")
(COMMAND "POINT" "5.601715,5.567476,-0.180222")
(COMMAND "POINT" "5.867625,5.569100,-0.181855")
(COMMAND "POINT" "6.127403,5.569495,-0.183261")
(COMMAND "POINT" "6.381049,5.568661,-0.184442")
(COMMAND "POINT" "6.628563,5.566597,-0.185397")
(COMMAND "POINT" "6.869946,5.563305,-0.186126")
(COMMAND "POINT" "7.105197,5.558783,-0.186629")
(COMMAND "POINT" "7.334315,5.553032,-0.186907")
(COMMAND "POINT" "7.557302,5.546052,-0.186959")
(COMMAND "POINT" "7.774158,5.537843,-0.186785")
(COMMAND "POINT" "7.984881,5.528404,-0.186385")
(COMMAND "POINT" "8.189473,5.517737,-0.185759")
(COMMAND "POINT" "8.387932,5.505840,-0.184908")
(COMMAND "POINT" "8.580260,5.492714,-0.183830")
(COMMAND "POINT" "8.766456,5.478359,-0.182527")
(COMMAND "POINT" "8.946521,5.462775,-0.180998")
(COMMAND "POINT" "9.120453,5.445961,-0.179243")
(COMMAND "POINT" "9.288254,5.427918,-0.177263")
(COMMAND "POINT" "9.449922,5.408646,-0.175057")
(COMMAND "POINT" "9.605459,5.388145,-0.172624")
(COMMAND "POINT" "9.754864,5.366415,-0.169966")
(COMMAND "POINT" "9.898138,5.343456,-0.167083")
(COMMAND "POINT" "10.035279,5.319267,-0.163973")
(COMMAND "POINT" "10.166289,5.293849,-0.160638")
(COMMAND "POINT" "10.291166,5.267202,-0.157076")
(COMMAND "POINT" "10.409912,5.239326,-0.153289")
(COMMAND "POINT" "10.522526,5.210221,-0.149277")
(COMMAND "POINT" "10.629009,5.179886,-0.145038")
(COMMAND "POINT" "10.729359,5.148322,-0.140573")
(COMMAND "POINT" "10.823578,5.115530,-0.135883")
(COMMAND "POINT" "10.911664,5.081507,-0.130967")
(COMMAND "POINT" "10.993619,5.046256,-0.125825")
(COMMAND "POINT" "11.069442,5.009776,-0.120458")
(COMMAND "POINT" "11.139134,4.972066,-0.114864")
(COMMAND "POINT" "11.202693,4.933127,-0.109045")
(COMMAND "POINT" "11.260913,4.893363,-0.103048")
(COMMAND "POINT" "11.318545,4.855194,-0.097160")
(COMMAND "POINT" "11.376381,4.819024,-0.091430")
(COMMAND "POINT" "11.434423,4.784854,-0.085858")
(COMMAND "POINT" "11.492668,4.752682,-0.080444")
(COMMAND "POINT" "11.551118,4.722510,-0.075187")
(COMMAND "POINT" "11.609773,4.694337,-0.070088")
(COMMAND "POINT" "11.668632,4.668163,-0.065147")
(COMMAND "POINT" "11.727696,4.643988,-0.060363")
(COMMAND "POINT" "11.786964,4.621812,-0.055737")
(COMMAND "POINT" "11.846437,4.601636,-0.051269")
(COMMAND "POINT" "11.906114,4.583458,-0.046958")
(COMMAND "POINT" "11.965996,4.567280,-0.042806")
(COMMAND "POINT" "12.026082,4.553101,-0.038810")
(COMMAND "POINT" "12.086373,4.540921,-0.034973")
(COMMAND "POINT" "12.146868,4.530740,-0.031293")
(COMMAND "POINT" "12.207568,4.522558,-0.027771")
(COMMAND "POINT" "12.268472,4.516376,-0.024406")
(COMMAND "POINT" "12.329581,4.512193,-0.021199")
(COMMAND "POINT" "12.390894,4.510008,-0.018150")
(COMMAND "POINT" "12.452412,4.509823,-0.015259")
(COMMAND "POINT" "12.514135,4.511637,-0.012525")
(COMMAND "POINT" "12.576061,4.515450,-0.009949")
(COMMAND "POINT" "12.638193,4.521263,-0.007531")
(COMMAND "POINT" "12.700529,4.529074,-0.005270")
(COMMAND "POINT" "12.763069,4.538885,-0.003167")
(COMMAND "POINT" "12.825814,4.550694,-0.001222")
(COMMAND "POINT" "12.888763,4.564503,0.000566")
(COMMAND "POINT" "12.951917,4.580311,0.002196")
(COMMAND "POINT" "13.015276,4.598118,0.003668")
(COMMAND "POINT" "13.078839,4.617925,0.004983")
(COMMAND "POINT" "13.142606,4.639730,0.006140")
(COMMAND "POINT" "13.206578,4.663535,0.007139")
(COMMAND "POINT" "13.270755,4.689339,0.007980")
(COMMAND "POINT" "13.335136,4.717141,0.008664")
(COMMAND "POINT" "13.399721,4.746944,0.009190")
(COMMAND "POINT" "13.464512,4.778745,0.009559")
(COMMAND "POINT" "13.529506,4.812545,0.009770")
(COMMAND "POINT" "13.594705,4.848344,0.009823")
(COMMAND "POINT" "13.660109,4.886143,0.009718")
(COMMAND "POINT" "13.725717,4.925941,0.009456")
(COMMAND "POINT" "13.791529,4.967738,0.009036")
(COMMAND "POINT" "13.857547,5.011534,0.008458")
(COMMAND "POINT" "13.923768,5.057329,0.007723")
(COMMAND "POINT" "13.990194,5.105123,0.006830")
(COMMAND "POINT" "14.056825,5.154917,0.005780")
(COMMAND "POINT" "14.123660,5.206709,0.004571")
(COMMAND "POINT" "14.190700,5.260501,0.003205")
(COMMAND "POINT" "14.257944,5.316292,0.001681")
(COMMAND "POINT" "14.325393,5.374082,0.000000")
(COMMAND "POINT" "1.181631,5.797814,-0.125749")
(COMMAND "POINT" "1.523541,5.804194,-0.130656")
(COMMAND "POINT" "1.859649,5.809740,-0.135342")
(COMMAND "POINT" "2.189954,5.814453,-0.139807")
(COMMAND "POINT" "2.514456,5.818332,-0.144052")
(COMMAND "POINT" "2.833154,5.821377,-0.148076")
(COMMAND "POINT" "3.146050,5.823589,-0.151879")
(COMMAND "POINT" "3.453142,5.824967,-0.155461")
(COMMAND "POINT" "3.754432,5.825511,-0.158823")
(COMMAND "POINT" "4.049918,5.825221,-0.161964")
(COMMAND "POINT" "4.339601,5.824098,-0.164884")
(COMMAND "POINT" "4.623481,5.822141,-0.167583")
(COMMAND "POINT" "4.901559,5.819350,-0.170062")
(COMMAND "POINT" "5.173833,5.815726,-0.172320")
(COMMAND "POINT" "5.440304,5.811268,-0.174357")
(COMMAND "POINT" "5.700972,5.805976,-0.176174")
(COMMAND "POINT" "5.955837,5.799851,-0.177769")
(COMMAND "POINT" "6.204899,5.792891,-0.179144")
(COMMAND "POINT" "6.448158,5.785098,-0.180299")
(COMMAND "POINT" "6.685613,5.776472,-0.181232")
(COMMAND "POINT" "6.917266,5.767011,-0.181945")
(COMMAND "POINT" "7.143116,5.756717,-0.182437")
(COMMAND "POINT" "7.363162,5.745589,-0.182708")
(COMMAND "POINT" "7.577406,5.733628,-0.182759")
(COMMAND "POINT" "7.785846,5.720832,-0.182589")
(COMMAND "POINT" "7.988484,5.707203,-0.182198")
(COMMAND "POINT" "8.185318,5.692741,-0.181586")
(COMMAND "POINT" "8.376350,5.677444,-0.180754")
(COMMAND "POINT" "8.561578,5.661314,-0.179701")
(COMMAND "POINT" "8.741003,5.644350,-0.178427")
(COMMAND "POINT" "8.914625,5.626553,-0.176932")
(COMMAND "POINT" "9.082444,5.607922,-0.175217")
(COMMAND "POINT" "9.244460,5.588457,-0.173281")
(COMMAND "POINT" "9.400673,5.568158,-0.171124")
(COMMAND "POINT" "9.551083,5.547026,-0.168746")
(COMMAND "POINT" "9.695690,5.525060,-0.166148")
(COMMAND "POINT" "9.834494,5.502260,-0.163329")
(COMMAND "POINT" "9.967495,5.478626,-0.160289")
(COMMAND "POINT" "10.094692,5.454159,-0.157029")
(COMMAND "POINT" "10.216087,5.428858,-0.153548")
(COMMAND "POINT" "10.331678,5.402723,-0.149846")
(COMMAND "POINT" "10.441467,5.375755,-0.145923")
(COMMAND "POINT" "10.545452,5.347953,-0.141780")
(COMMAND "POINT" "10.643635,5.319317,-0.137416")
(COMMAND "POINT" "10.736014,5.289847,-0.132831")
(COMMAND "POINT" "10.822590,5.259544,-0.128025")
(COMMAND "POINT" "10.903364,5.228407,-0.122999")
(COMMAND "POINT" "10.978334,5.196437,-0.117752")
(COMMAND "POINT" "11.047501,5.163632,-0.112284")
(COMMAND "POINT" "11.110865,5.129994,-0.106595")
(COMMAND "POINT" "11.169167,5.095869,-0.100733")
(COMMAND "POINT" "11.226850,5.063335,-0.094978")
(COMMAND "POINT" "11.284655,5.032738,-0.089376")
(COMMAND "POINT" "11.342583,5.004079,-0.083930")
(COMMAND "POINT" "11.400634,4.977358,-0.078637")
(COMMAND "POINT" "11.458806,4.952574,-0.073498")
(COMMAND "POINT" "11.517101,4.929728,-0.068514")
(COMMAND "POINT" "11.575518,4.908820,-0.063683")
(COMMAND "POINT" "11.634058,4.889849,-0.059007")
(COMMAND "POINT" "11.692720,4.872816,-0.054485")
(COMMAND "POINT" "11.751504,4.857721,-0.050117")
(COMMAND "POINT" "11.810411,4.844563,-0.045904")
(COMMAND "POINT" "11.869439,4.833343,-0.041844")
(COMMAND "POINT" "11.928591,4.824061,-0.037938")
(COMMAND "POINT" "11.987864,4.816716,-0.034187")
(COMMAND "POINT" "12.047260,4.811309,-0.030590")
(COMMAND "POINT" "12.106778,4.807839,-0.027147")
(COMMAND "POINT" "12.166419,4.806307,-0.023858")
(COMMAND "POINT" "12.226181,4.806713,-0.020723")
(COMMAND "POINT" "12.286066,4.809056,-0.017743")
(COMMAND "POINT" "12.346074,4.813337,-0.014916")
(COMMAND "POINT" "12.406204,4.819556,-0.012244")
(COMMAND "POINT" "12.466456,4.827712,-0.009726")
(COMMAND "POINT" "12.526830,4.837806,-0.007362")
(COMMAND "POINT" "12.587327,4.849838,-0.005152")
(COMMAND "POINT" "12.647946,4.863807,-0.003096")
(COMMAND "POINT" "12.708687,4.879714,-0.001194")
(COMMAND "POINT" "12.769551,4.897558,0.000553")
(COMMAND "POINT" "12.830537,4.917340,0.002147")
(COMMAND "POINT" "12.891645,4.939060,0.003586")
(COMMAND "POINT" "12.952876,4.962718,0.004871")
(COMMAND "POINT" "13.014229,4.988313,0.006002")
(COMMAND "POINT" "13.075704,5.015845,0.006979")
(COMMAND "POINT" "13.137302,5.045316,0.007801")
(COMMAND "POINT" "13.199022,5.076724,0.008470")
(COMMAND "POINT" "13.260864,5.110069,0.008984")
(COMMAND "POINT" "13.322828,5.145353,0.009344")
(COMMAND "POINT" "13.384915,5.182573,0.009550")
(COMMAND "POINT" "13.447125,5.221732,0.009602")
(COMMAND "POINT" "13.509456,5.262828,0.009500")
(COMMAND "POINT" "13.571910,5.305862,0.009244")
(COMMAND "POINT" "13.634486,5.350833,0.008833")
(COMMAND "POINT" "13.697185,5.397743,0.008268")
(COMMAND "POINT" "13.760005,5.446589,0.007550")
(COMMAND "POINT" "13.822949,5.497374,0.006677")
(COMMAND "POINT" "13.886014,5.550096,0.005650")
(COMMAND "POINT" "13.949202,5.604755,0.004468")
(COMMAND "POINT" "14.012512,5.661353,0.003133")
(COMMAND "POINT" "14.075944,5.719888,0.001644")
(COMMAND "POINT" "14.139499,5.780360,0.000000")
(COMMAND "POINT" "1.474084,6.190451,-0.121574")
(COMMAND "POINT" "1.800487,6.183798,-0.126317")
(COMMAND "POINT" "2.121408,6.176690,-0.130848")
(COMMAND "POINT" "2.436847,6.169124,-0.135165")
(COMMAND "POINT" "2.746803,6.161103,-0.139268")
(COMMAND "POINT" "3.051278,6.152625,-0.143159")
(COMMAND "POINT" "3.350271,6.143690,-0.146836")
(COMMAND "POINT" "3.643782,6.134299,-0.150299")
(COMMAND "POINT" "3.931811,6.124452,-0.153549")
(COMMAND "POINT" "4.214357,6.114149,-0.156586")
(COMMAND "POINT" "4.491422,6.103389,-0.159409")
(COMMAND "POINT" "4.763005,6.092172,-0.162018")
(COMMAND "POINT" "5.029106,6.080500,-0.164415")
(COMMAND "POINT" "5.289725,6.068371,-0.166598")
(COMMAND "POINT" "5.544861,6.055785,-0.168567")
(COMMAND "POINT" "5.794516,6.042743,-0.170323")
(COMMAND "POINT" "6.038689,6.029245,-0.171866")
(COMMAND "POINT" "6.277379,6.015290,-0.173196")
(COMMAND "POINT" "6.510588,6.000879,-0.174312")
(COMMAND "POINT" "6.738315,5.986012,-0.175214")
(COMMAND "POINT" "6.960560,5.970688,-0.175903")
(COMMAND "POINT" "7.177322,5.954908,-0.176379")
(COMMAND "POINT" "7.388603,5.938671,-0.176641")
(COMMAND "POINT" "7.594401,5.921978,-0.176690")
(COMMAND "POINT" "7.794718,5.904829,-0.176526")
(COMMAND "POINT" "7.989553,5.887223,-0.176148")
(COMMAND "POINT" "8.178905,5.869161,-0.175556")
(COMMAND "POINT" "8.362776,5.850643,-0.174752")
(COMMAND "POINT" "8.541165,5.831668,-0.173733")
(COMMAND "POINT" "8.714071,5.812237,-0.172502")
(COMMAND "POINT" "8.881496,5.792349,-0.171057")
(COMMAND "POINT" "9.043438,5.772005,-0.169399")
(COMMAND "POINT" "9.199899,5.751205,-0.167527")
(COMMAND "POINT" "9.350877,5.729948,-0.165442")
(COMMAND "POINT" "9.496374,5.708235,-0.163143")
(COMMAND "POINT" "9.636388,5.686065,-0.160631")
(COMMAND "POINT" "9.770921,5.663439,-0.157906")
(COMMAND "POINT" "9.899972,5.640357,-0.154967")
(COMMAND "POINT" "10.023540,5.616818,-0.151815")
(COMMAND "POINT" "10.141626,5.592823,-0.148449")
(COMMAND "POINT" "10.254231,5.568371,-0.144870")
(COMMAND "POINT" "10.361353,5.543464,-0.141078")
(COMMAND "POINT" "10.462994,5.518099,-0.137072")
(COMMAND "POINT" "10.559152,5.492279,-0.132853")
(COMMAND "POINT" "10.649829,5.466002,-0.128420")
(COMMAND "POINT" "10.735023,5.439268,-0.123774")
(COMMAND "POINT" "10.814736,5.412078,-0.118914")
(COMMAND "POINT" "10.888966,5.384432,-0.113841")
(COMMAND "POINT" "10.957714,5.356330,-0.108555")
(COMMAND "POINT" "11.020981,5.327771,-0.103056")
(COMMAND "POINT" "11.079456,5.299047,-0.097388")
(COMMAND "POINT" "11.137283,5.271911,-0.091824")
(COMMAND "POINT" "11.195153,5.246653,-0.086409")
(COMMAND "POINT" "11.253066,5.223275,-0.081143")
(COMMAND "POINT" "11.311022,5.201775,-0.076026")
(COMMAND "POINT" "11.369021,5.182154,-0.071058")
(COMMAND "POINT" "11.427063,5.164412,-0.066239")
(COMMAND "POINT" "11.485147,5.148549,-0.061569")
(COMMAND "POINT" "11.543275,5.134565,-0.057048")
(COMMAND "POINT" "11.601445,5.122460,-0.052676")
(COMMAND "POINT" "11.659658,5.112234,-0.048453")
(COMMAND "POINT" "11.717914,5.103886,-0.044379")
(COMMAND "POINT" "11.776213,5.097418,-0.040454")
(COMMAND "POINT" "11.834555,5.092828,-0.036679")
(COMMAND "POINT" "11.892940,5.090118,-0.033052")
(COMMAND "POINT" "11.951367,5.089286,-0.029574")
(COMMAND "POINT" "12.009838,5.090333,-0.026245")
(COMMAND "POINT" "12.068351,5.093259,-0.023066")
(COMMAND "POINT" "12.126907,5.098064,-0.020035")
(COMMAND "POINT" "12.185506,5.104748,-0.017153")
(COMMAND "POINT" "12.244148,5.113311,-0.014421")
(COMMAND "POINT" "12.302833,5.123752,-0.011837")
(COMMAND "POINT" "12.361561,5.136073,-0.009403")
(COMMAND "POINT" "12.420332,5.150273,-0.007117")
(COMMAND "POINT" "12.479145,5.166351,-0.004981")
(COMMAND "POINT" "12.538002,5.184308,-0.002993")
(COMMAND "POINT" "12.596901,5.204144,-0.001155")
(COMMAND "POINT" "12.655843,5.225860,0.000535")
(COMMAND "POINT" "12.714828,5.249454,0.002075")
(COMMAND "POINT" "12.773856,5.274927,0.003467")
(COMMAND "POINT" "12.832927,5.302278,0.004709")
(COMMAND "POINT" "12.892040,5.331509,0.005802")
(COMMAND "POINT" "12.951197,5.362619,0.006747")
(COMMAND "POINT" "13.010396,5.395607,0.007542")
(COMMAND "POINT" "13.069639,5.430475,0.008188")
(COMMAND "POINT" "13.128924,5.467221,0.008686")
(COMMAND "POINT" "13.188252,5.505846,0.009034")
(COMMAND "POINT" "13.247623,5.546350,0.009233")
(COMMAND "POINT" "13.307037,5.588734,0.009283")
(COMMAND "POINT" "13.366494,5.632996,0.009185")
(COMMAND "POINT" "13.425993,5.679136,0.008937")
(COMMAND "POINT" "13.485536,5.727156,0.008540")
(COMMAND "POINT" "13.545121,5.777055,0.007994")
(COMMAND "POINT" "13.604749,5.828832,0.007299")
(COMMAND "POINT" "13.664420,5.882489,0.006455")
(COMMAND "POINT" "13.724134,5.938024,0.005462")
(COMMAND "POINT" "13.783891,5.995439,0.004320")
(COMMAND "POINT" "13.843691,6.054732,0.003029")
(COMMAND "POINT" "13.903534,6.115904,0.001589")
(COMMAND "POINT" "13.963419,6.178955,0.000000")
(COMMAND "POINT" "1.754607,6.573522,-0.116112")
(COMMAND "POINT" "2.065970,6.554486,-0.120643")
(COMMAND "POINT" "2.372165,6.535353,-0.124970")
(COMMAND "POINT" "2.673191,6.516123,-0.129093")
(COMMAND "POINT" "2.969049,6.496795,-0.133012")
(COMMAND "POINT" "3.259737,6.477370,-0.136728")
(COMMAND "POINT" "3.545257,6.457848,-0.140239")
(COMMAND "POINT" "3.825609,6.438229,-0.143547")
(COMMAND "POINT" "4.100792,6.418513,-0.146651")
(COMMAND "POINT" "4.370806,6.398699,-0.149551")
(COMMAND "POINT" "4.635651,6.378789,-0.152247")
(COMMAND "POINT" "4.895327,6.358781,-0.154740")
(COMMAND "POINT" "5.149835,6.338676,-0.157029")
(COMMAND "POINT" "5.399175,6.318473,-0.159114")
(COMMAND "POINT" "5.643345,6.298174,-0.160995")
(COMMAND "POINT" "5.882347,6.277777,-0.162672")
(COMMAND "POINT" "6.116180,6.257283,-0.164145")
(COMMAND "POINT" "6.344845,6.236692,-0.165415")
(COMMAND "POINT" "6.568340,6.216004,-0.166481")
(COMMAND "POINT" "6.786668,6.195218,-0.167343")
(COMMAND "POINT" "6.999826,6.174336,-0.168001")
(COMMAND "POINT" "7.207816,6.153356,-0.168455")
(COMMAND "POINT" "7.410637,6.132279,-0.168706")
(COMMAND "POINT" "7.608289,6.111104,-0.168752")
(COMMAND "POINT" "7.800773,6.089833,-0.168595")
(COMMAND "POINT" "7.988088,6.068464,-0.168234")
(COMMAND "POINT" "8.170234,6.046998,-0.167670")
(COMMAND "POINT" "8.347212,6.025435,-0.166901")
(COMMAND "POINT" "8.519021,6.003775,-0.165929")
(COMMAND "POINT" "8.685661,5.982018,-0.164752")
(COMMAND "POINT" "8.847132,5.960163,-0.163372")
(COMMAND "POINT" "9.003435,5.938211,-0.161789")
(COMMAND "POINT" "9.154569,5.916162,-0.160001")
(COMMAND "POINT" "9.300535,5.894016,-0.158009")
(COMMAND "POINT" "9.441332,5.871772,-0.155814")
(COMMAND "POINT" "9.576960,5.849432,-0.153415")
(COMMAND "POINT" "9.707419,5.826994,-0.150812")
(COMMAND "POINT" "9.832710,5.804459,-0.148005")
(COMMAND "POINT" "9.952832,5.781827,-0.144995")
(COMMAND "POINT" "10.067785,5.759097,-0.141780")
(COMMAND "POINT" "10.177570,5.736271,-0.138362")
(COMMAND "POINT" "10.282186,5.713347,-0.134740")
(COMMAND "POINT" "10.381633,5.690326,-0.130914")
(COMMAND "POINT" "10.475912,5.667208,-0.126884")
(COMMAND "POINT" "10.565022,5.643992,-0.122651")
(COMMAND "POINT" "10.648963,5.620680,-0.118213")
(COMMAND "POINT" "10.727735,5.597270,-0.113572")
(COMMAND "POINT" "10.801339,5.573763,-0.108727")
(COMMAND "POINT" "10.869774,5.550159,-0.103679")
(COMMAND "POINT" "10.933041,5.526457,-0.098426")
(COMMAND "POINT" "10.991780,5.502899,-0.093013")
(COMMAND "POINT" "11.049844,5.480923,-0.087699")
(COMMAND "POINT" "11.107875,5.460770,-0.082527")
(COMMAND "POINT" "11.165871,5.442441,-0.077497")
(COMMAND "POINT" "11.223833,5.425934,-0.072610")
(COMMAND "POINT" "11.281762,5.411250,-0.067865")
(COMMAND "POINT" "11.339657,5.398389,-0.063263")
(COMMAND "POINT" "11.397518,5.387351,-0.058803")
(COMMAND "POINT" "11.455345,5.378136,-0.054485")
(COMMAND "POINT" "11.513139,5.370744,-0.050310")
(COMMAND "POINT" "11.570899,5.365175,-0.046276")
(COMMAND "POINT" "11.628624,5.361428,-0.042386")
(COMMAND "POINT" "11.686317,5.359505,-0.038637")
(COMMAND "POINT" "11.743975,5.359405,-0.035031")
(COMMAND "POINT" "11.801599,5.361127,-0.031567")
(COMMAND "POINT" "11.859190,5.364673,-0.028246")
(COMMAND "POINT" "11.916747,5.370041,-0.025066")
(COMMAND "POINT" "11.974270,5.377232,-0.022030")
(COMMAND "POINT" "12.031759,5.386247,-0.019135")
(COMMAND "POINT" "12.089214,5.397084,-0.016383")
(COMMAND "POINT" "12.146636,5.409744,-0.013773")
(COMMAND "POINT" "12.204023,5.424227,-0.011305")
(COMMAND "POINT" "12.261377,5.440533,-0.008980")
(COMMAND "POINT" "12.318698,5.458662,-0.006797")
(COMMAND "POINT" "12.375984,5.478614,-0.004757")
(COMMAND "POINT" "12.433236,5.500389,-0.002859")
(COMMAND "POINT" "12.490455,5.523987,-0.001103")
(COMMAND "POINT" "12.547640,5.549407,0.000511")
(COMMAND "POINT" "12.604791,5.576651,0.001982")
(COMMAND "POINT" "12.661908,5.605718,0.003311")
(COMMAND "POINT" "12.718992,5.636607,0.004498")
(COMMAND "POINT" "12.776041,5.669320,0.005542")
(COMMAND "POINT" "12.833057,5.703855,0.006444")
(COMMAND "POINT" "12.890039,5.740213,0.007203")
(COMMAND "POINT" "12.946987,5.778395,0.007821")
(COMMAND "POINT" "13.003902,5.818399,0.008295")
(COMMAND "POINT" "13.060782,5.860226,0.008628")
(COMMAND "POINT" "13.117629,5.903876,0.008818")
(COMMAND "POINT" "13.174442,5.949349,0.008866")
(COMMAND "POINT" "13.231221,5.996645,0.008772")
(COMMAND "POINT" "13.287967,6.045764,0.008535")
(COMMAND "POINT" "13.344678,6.096706,0.008156")
(COMMAND "POINT" "13.401356,6.149471,0.007635")
(COMMAND "POINT" "13.458000,6.204058,0.006971")
(COMMAND "POINT" "13.514610,6.260469,0.006165")
(COMMAND "POINT" "13.571186,6.318703,0.005217")
(COMMAND "POINT" "13.627729,6.378759,0.004126")
(COMMAND "POINT" "13.684237,6.440639,0.002893")
(COMMAND "POINT" "13.740712,6.504341,0.001518")
(COMMAND "POINT" "13.797153,6.569866,0.000000")
(COMMAND "POINT" "2.023199,6.947028,-0.109365")
(COMMAND "POINT" "2.319992,6.916257,-0.113632")
(COMMAND "POINT" "2.611921,6.885731,-0.117708")
(COMMAND "POINT" "2.898988,6.855448,-0.121591")
(COMMAND "POINT" "3.181191,6.825409,-0.125283")
(COMMAND "POINT" "3.458532,6.795615,-0.128782")
(COMMAND "POINT" "3.731009,6.766064,-0.132090")
(COMMAND "POINT" "3.998623,6.736756,-0.135205")
(COMMAND "POINT" "4.261374,6.707693,-0.138129")
(COMMAND "POINT" "4.519262,6.678874,-0.140861")
(COMMAND "POINT" "4.772287,6.650298,-0.143400")
(COMMAND "POINT" "5.020449,6.621966,-0.145748")
(COMMAND "POINT" "5.263747,6.593878,-0.147904")
(COMMAND "POINT" "5.502183,6.566034,-0.149867")
(COMMAND "POINT" "5.735755,6.538434,-0.151639")
(COMMAND "POINT" "5.964465,6.511078,-0.153219")
(COMMAND "POINT" "6.188311,6.483965,-0.154607")
(COMMAND "POINT" "6.407294,6.457097,-0.155803")
(COMMAND "POINT" "6.621415,6.430472,-0.156806")
(COMMAND "POINT" "6.830672,6.404091,-0.157618")
(COMMAND "POINT" "7.035066,6.377954,-0.158238")
(COMMAND "POINT" "7.234596,6.352060,-0.158666")
(COMMAND "POINT" "7.429264,6.326411,-0.158902")
(COMMAND "POINT" "7.619069,6.301005,-0.158946")
(COMMAND "POINT" "7.804010,6.275844,-0.158798")
(COMMAND "POINT" "7.984089,6.250926,-0.158458")
(COMMAND "POINT" "8.159304,6.226252,-0.157926")
(COMMAND "POINT" "8.329657,6.201822,-0.157202")
(COMMAND "POINT" "8.495146,6.177636,-0.156286")
(COMMAND "POINT" "8.655772,6.153693,-0.155179")
(COMMAND "POINT" "8.811535,6.129995,-0.153879")
(COMMAND "POINT" "8.962435,6.106540,-0.152387")
(COMMAND "POINT" "9.108472,6.083329,-0.150703")
(COMMAND "POINT" "9.249645,6.060362,-0.148827")
(COMMAND "POINT" "9.385956,6.037639,-0.146760")
(COMMAND "POINT" "9.517404,6.015160,-0.144500")
(COMMAND "POINT" "9.643988,5.992924,-0.142048")
(COMMAND "POINT" "9.765710,5.970933,-0.139404")
(COMMAND "POINT" "9.882568,5.949185,-0.136569")
(COMMAND "POINT" "9.994563,5.927681,-0.133541")
(COMMAND "POINT" "10.101695,5.906421,-0.130322")
(COMMAND "POINT" "10.203964,5.885405,-0.126910")
(COMMAND "POINT" "10.301370,5.864632,-0.123306")
(COMMAND "POINT" "10.393913,5.844104,-0.119511")
(COMMAND "POINT" "10.481593,5.823819,-0.115523")
(COMMAND "POINT" "10.564409,5.803778,-0.111344")
(COMMAND "POINT" "10.642363,5.783981,-0.106972")
(COMMAND "POINT" "10.715453,5.764428,-0.102409")
(COMMAND "POINT" "10.783681,5.745119,-0.097654")
(COMMAND "POINT" "10.847045,5.726054,-0.092706")
(COMMAND "POINT" "10.906140,5.707423,-0.087608")
(COMMAND "POINT" "10.964534,5.690371,-0.082602")
(COMMAND "POINT" "11.022820,5.675089,-0.077731")
(COMMAND "POINT" "11.080997,5.661577,-0.072994")
(COMMAND "POINT" "11.139068,5.649834,-0.068391")
(COMMAND "POINT" "11.197030,5.639861,-0.063922")
(COMMAND "POINT" "11.254885,5.631658,-0.059587")
(COMMAND "POINT" "11.312632,5.625225,-0.055386")
(COMMAND "POINT" "11.370271,5.620561,-0.051319")
(COMMAND "POINT" "11.427802,5.617667,-0.047386")
(COMMAND "POINT" "11.485226,5.616543,-0.043587")
(COMMAND "POINT" "11.542542,5.617189,-0.039923")
(COMMAND "POINT" "11.599750,5.619604,-0.036392")
(COMMAND "POINT" "11.656850,5.623789,-0.032995")
(COMMAND "POINT" "11.713843,5.629744,-0.029733")
(COMMAND "POINT" "11.770728,5.637468,-0.026604")
(COMMAND "POINT" "11.827505,5.646963,-0.023610")
(COMMAND "POINT" "11.884174,5.658227,-0.020749")
(COMMAND "POINT" "11.940736,5.671260,-0.018023")
(COMMAND "POINT" "11.997190,5.686064,-0.015431")
(COMMAND "POINT" "12.053536,5.702637,-0.012973")
(COMMAND "POINT" "12.109774,5.720980,-0.010649")
(COMMAND "POINT" "12.165905,5.741093,-0.008458")
(COMMAND "POINT" "12.221928,5.762975,-0.006402")
(COMMAND "POINT" "12.277843,5.786627,-0.004480")
(COMMAND "POINT" "12.333650,5.812049,-0.002693")
(COMMAND "POINT" "12.389350,5.839240,-0.001039")
(COMMAND "POINT" "12.444942,5.868202,0.000481")
(COMMAND "POINT" "12.500426,5.898933,0.001867")
(COMMAND "POINT" "12.555802,5.931434,0.003119")
(COMMAND "POINT" "12.611071,5.965704,0.004236")
(COMMAND "POINT" "12.666232,6.001744,0.005220")
(COMMAND "POINT" "12.721285,6.039554,0.006069")
(COMMAND "POINT" "12.776230,6.079134,0.006785")
(COMMAND "POINT" "12.831068,6.120484,0.007366")
(COMMAND "POINT" "12.885798,6.163603,0.007813")
(COMMAND "POINT" "12.940420,6.208492,0.008127")
(COMMAND "POINT" "12.994934,6.255151,0.008306")
(COMMAND "POINT" "13.049341,6.303579,0.008351")
(COMMAND "POINT" "13.103639,6.353777,0.008262")
(COMMAND "POINT" "13.157830,6.405745,0.008039")
(COMMAND "POINT" "13.211914,6.459483,0.007682")
(COMMAND "POINT" "13.265889,6.514990,0.007191")
(COMMAND "POINT" "13.319757,6.572267,0.006566")
(COMMAND "POINT" "13.373517,6.631314,0.005807")
(COMMAND "POINT" "13.427170,6.692130,0.004914")
(COMMAND "POINT" "13.480714,6.754717,0.003886")
(COMMAND "POINT" "13.534151,6.819073,0.002725")
(COMMAND "POINT" "13.587480,6.885198,0.001429")
(COMMAND "POINT" "13.640701,6.953094,0.000000")
(COMMAND "POINT" "2.279860,7.310967,-0.101331")
(COMMAND "POINT" "2.562551,7.269111,-0.105285")
(COMMAND "POINT" "2.840676,7.227823,-0.109062")
(COMMAND "POINT" "3.114236,7.187101,-0.112660")
(COMMAND "POINT" "3.383231,7.146946,-0.116080")
(COMMAND "POINT" "3.647661,7.107357,-0.119323")
(COMMAND "POINT" "3.907525,7.068336,-0.122387")
(COMMAND "POINT" "4.162824,7.029881,-0.125274")
(COMMAND "POINT" "4.413558,6.991992,-0.127983")
(COMMAND "POINT" "4.659727,6.954671,-0.130514")
(COMMAND "POINT" "4.901330,6.917917,-0.132867")
(COMMAND "POINT" "5.138369,6.881729,-0.135042")
(COMMAND "POINT" "5.370842,6.846108,-0.137040")
(COMMAND "POINT" "5.598750,6.811053,-0.138859")
(COMMAND "POINT" "5.822092,6.776566,-0.140501")
(COMMAND "POINT" "6.040870,6.742645,-0.141964")
(COMMAND "POINT" "6.255082,6.709291,-0.143250")
(COMMAND "POINT" "6.464729,6.676504,-0.144358")
(COMMAND "POINT" "6.669810,6.644283,-0.145288")
(COMMAND "POINT" "6.870327,6.612629,-0.146041")
(COMMAND "POINT" "7.066278,6.581542,-0.146615")
(COMMAND "POINT" "7.257664,6.551022,-0.147012")
(COMMAND "POINT" "7.444485,6.521069,-0.147230")
(COMMAND "POINT" "7.626741,6.491682,-0.147271")
(COMMAND "POINT" "7.804431,6.462862,-0.147134")
(COMMAND "POINT" "7.977556,6.434609,-0.146819")
(COMMAND "POINT" "8.146116,6.406922,-0.146326")
(COMMAND "POINT" "8.310111,6.379803,-0.145655")
(COMMAND "POINT" "8.469540,6.353250,-0.144807")
(COMMAND "POINT" "8.624405,6.327263,-0.143780")
(COMMAND "POINT" "8.774704,6.301844,-0.142576")
(COMMAND "POINT" "8.920437,6.276991,-0.141194")
(COMMAND "POINT" "9.061606,6.252706,-0.139633")
(COMMAND "POINT" "9.198209,6.228986,-0.137895")
(COMMAND "POINT" "9.330248,6.205834,-0.135980")
(COMMAND "POINT" "9.457720,6.183249,-0.133886")
(COMMAND "POINT" "9.580628,6.161230,-0.131614")
(COMMAND "POINT" "9.698971,6.139778,-0.129165")
(COMMAND "POINT" "9.812748,6.118892,-0.126537")
(COMMAND "POINT" "9.921960,6.098574,-0.123732")
(COMMAND "POINT" "10.026607,6.078822,-0.120749")
(COMMAND "POINT" "10.126688,6.059637,-0.117588")
(COMMAND "POINT" "10.222205,6.041019,-0.114249")
(COMMAND "POINT" "10.313156,6.022967,-0.110732")
(COMMAND "POINT" "10.399542,6.005482,-0.107038")
(COMMAND "POINT" "10.481362,5.988564,-0.103165")
(COMMAND "POINT" "10.558618,5.972213,-0.099115")
(COMMAND "POINT" "10.631308,5.956429,-0.094887")
(COMMAND "POINT" "10.699433,5.941211,-0.090481")
(COMMAND "POINT" "10.762993,5.926560,-0.085897")
(COMMAND "POINT" "10.822536,5.912620,-0.081173")
(COMMAND "POINT" "10.881351,5.900255,-0.076535")
(COMMAND "POINT" "10.939988,5.889610,-0.072021")
(COMMAND "POINT" "10.998446,5.880683,-0.067632")
(COMMAND "POINT" "11.056725,5.873476,-0.063367")
(COMMAND "POINT" "11.114825,5.867989,-0.059226")
(COMMAND "POINT" "11.172745,5.864220,-0.055210")
(COMMAND "POINT" "11.230487,5.862171,-0.051317")
(COMMAND "POINT" "11.288050,5.861841,-0.047549")
(COMMAND "POINT" "11.345435,5.863231,-0.043905")
(COMMAND "POINT" "11.402640,5.866340,-0.040386")
(COMMAND "POINT" "11.459666,5.871168,-0.036990")
(COMMAND "POINT" "11.516513,5.877715,-0.033719")
(COMMAND "POINT" "11.573181,5.885982,-0.030572")
(COMMAND "POINT" "11.629671,5.895968,-0.027549")
(COMMAND "POINT" "11.685981,5.907673,-0.024650")
(COMMAND "POINT" "11.742113,5.921098,-0.021876")
(COMMAND "POINT" "11.798065,5.936242,-0.019225")
(COMMAND "POINT" "11.853839,5.953105,-0.016699")
(COMMAND "POINT" "11.909433,5.971688,-0.014297")
(COMMAND "POINT" "11.964849,5.991989,-0.012020")
(COMMAND "POINT" "12.020086,6.014011,-0.009866")
(COMMAND "POINT" "12.075144,6.037751,-0.007837")
(COMMAND "POINT" "12.130022,6.063211,-0.005932")
(COMMAND "POINT" "12.184722,6.090390,-0.004151")
(COMMAND "POINT" "12.239243,6.119288,-0.002495")
(COMMAND "POINT" "12.293585,6.149906,-0.000962")
(COMMAND "POINT" "12.347748,6.182243,0.000446")
(COMMAND "POINT" "12.401733,6.216299,0.001730")
(COMMAND "POINT" "12.455538,6.252074,0.002889")
(COMMAND "POINT" "12.509164,6.289569,0.003925")
(COMMAND "POINT" "12.562611,6.328783,0.004836")
(COMMAND "POINT" "12.615880,6.369717,0.005623")
(COMMAND "POINT" "12.668969,6.412370,0.006286")
(COMMAND "POINT" "12.721879,6.456742,0.006825")
(COMMAND "POINT" "12.774611,6.502833,0.007239")
(COMMAND "POINT" "12.827164,6.550644,0.007530")
(COMMAND "POINT" "12.879537,6.600173,0.007696")
(COMMAND "POINT" "12.931732,6.651423,0.007738")
(COMMAND "POINT" "12.983748,6.704391,0.007655")
(COMMAND "POINT" "13.035584,6.759079,0.007449")
(COMMAND "POINT" "13.087242,6.815486,0.007118")
(COMMAND "POINT" "13.138721,6.873613,0.006663")
(COMMAND "POINT" "13.190021,6.933458,0.006084")
(COMMAND "POINT" "13.241142,6.995023,0.005380")
(COMMAND "POINT" "13.292084,7.058308,0.004553")
(COMMAND "POINT" "13.342847,7.123311,0.003601")
(COMMAND "POINT" "13.393432,7.190034,0.002525")
(COMMAND "POINT" "13.443837,7.258477,0.001324")
(COMMAND "POINT" "13.494063,7.328638,0.000000")
(COMMAND "POINT" "2.524591,7.665340,-0.092012")
(COMMAND "POINT" "2.793648,7.613049,-0.095603")
(COMMAND "POINT" "3.058430,7.561629,-0.099032")
(COMMAND "POINT" "3.318937,7.511080,-0.102299")
(COMMAND "POINT" "3.575168,7.461403,-0.105405")
(COMMAND "POINT" "3.827125,7.412598,-0.108349")
(COMMAND "POINT" "4.074806,7.364664,-0.111132")
(COMMAND "POINT" "4.318213,7.317602,-0.113753")
(COMMAND "POINT" "4.557344,7.271411,-0.116213")
(COMMAND "POINT" "4.792200,7.226092,-0.118511")
(COMMAND "POINT" "5.022781,7.181644,-0.120648")
(COMMAND "POINT" "5.249088,7.138068,-0.122623")
(COMMAND "POINT" "5.471119,7.095364,-0.124437")
(COMMAND "POINT" "5.688875,7.053530,-0.126089")
(COMMAND "POINT" "5.902355,7.012569,-0.127579")
(COMMAND "POINT" "6.111561,6.972479,-0.128909")
(COMMAND "POINT" "6.316492,6.933260,-0.130076")
(COMMAND "POINT" "6.517147,6.894913,-0.131082")
(COMMAND "POINT" "6.713528,6.857438,-0.131927")
(COMMAND "POINT" "6.905633,6.820834,-0.132610")
(COMMAND "POINT" "7.093464,6.785101,-0.133131")
(COMMAND "POINT" "7.277019,6.750241,-0.133491")
(COMMAND "POINT" "7.456299,6.716251,-0.133690")
(COMMAND "POINT" "7.631305,6.683133,-0.133727")
(COMMAND "POINT" "7.802035,6.650887,-0.133603")
(COMMAND "POINT" "7.968490,6.619512,-0.133316")
(COMMAND "POINT" "8.130669,6.589009,-0.132869")
(COMMAND "POINT" "8.288574,6.559377,-0.132260")
(COMMAND "POINT" "8.442204,6.530617,-0.131489")
(COMMAND "POINT" "8.591559,6.502728,-0.130557")
(COMMAND "POINT" "8.736638,6.475711,-0.129464")
(COMMAND "POINT" "8.877443,6.449566,-0.128208")
(COMMAND "POINT" "9.013972,6.424292,-0.126792")
(COMMAND "POINT" "9.146227,6.399889,-0.125214")
(COMMAND "POINT" "9.274206,6.376358,-0.123474")
(COMMAND "POINT" "9.397910,6.353699,-0.121573")
(COMMAND "POINT" "9.517339,6.331911,-0.119510")
(COMMAND "POINT" "9.632493,6.310994,-0.117286")
(COMMAND "POINT" "9.743372,6.290949,-0.114900")
(COMMAND "POINT" "9.849976,6.271776,-0.112353")
(COMMAND "POINT" "9.952305,6.253474,-0.109644")
(COMMAND "POINT" "10.050358,6.236044,-0.106774")
(COMMAND "POINT" "10.144137,6.219485,-0.103742")
(COMMAND "POINT" "10.233641,6.203798,-0.100549")
(COMMAND "POINT" "10.318869,6.188982,-0.097194")
(COMMAND "POINT" "10.399822,6.175038,-0.093678")
(COMMAND "POINT" "10.476501,6.161965,-0.090000")
(COMMAND "POINT" "10.548904,6.149764,-0.086160")
(COMMAND "POINT" "10.617032,6.138434,-0.082159")
(COMMAND "POINT" "10.680885,6.127976,-0.077997")
(COMMAND "POINT" "10.740967,6.118490,-0.073707")
(COMMAND "POINT" "10.800297,6.110575,-0.069496")
(COMMAND "POINT" "10.859380,6.104332,-0.065398")
(COMMAND "POINT" "10.918216,6.099760,-0.061412")
(COMMAND "POINT" "10.976805,6.096860,-0.057540")
(COMMAND "POINT" "11.035146,6.095631,-0.053780")
(COMMAND "POINT" "11.093239,6.096075,-0.050132")
(COMMAND "POINT" "11.151086,6.098190,-0.046598")
(COMMAND "POINT" "11.208684,6.101976,-0.043176")
(COMMAND "POINT" "11.266036,6.107434,-0.039868")
(COMMAND "POINT" "11.323140,6.114564,-0.036672")
(COMMAND "POINT" "11.379997,6.123365,-0.033588")
(COMMAND "POINT" "11.436606,6.133838,-0.030618")
(COMMAND "POINT" "11.492968,6.145983,-0.027760")
(COMMAND "POINT" "11.549083,6.159799,-0.025015")
(COMMAND "POINT" "11.604950,6.175287,-0.022383")
(COMMAND "POINT" "11.660570,6.192447,-0.019864")
(COMMAND "POINT" "11.715942,6.211278,-0.017457")
(COMMAND "POINT" "11.771067,6.231781,-0.015163")
(COMMAND "POINT" "11.825945,6.253955,-0.012983")
(COMMAND "POINT" "11.880575,6.277802,-0.010914")
(COMMAND "POINT" "11.934958,6.303319,-0.008959")
(COMMAND "POINT" "11.989093,6.330509,-0.007116")
(COMMAND "POINT" "12.042981,6.359370,-0.005387")
(COMMAND "POINT" "12.096622,6.389902,-0.003770")
(COMMAND "POINT" "12.150015,6.422107,-0.002265")
(COMMAND "POINT" "12.203161,6.455982,-0.000874")
(COMMAND "POINT" "12.256060,6.491530,0.000405")
(COMMAND "POINT" "12.308711,6.528749,0.001571")
(COMMAND "POINT" "12.361115,6.567640,0.002624")
(COMMAND "POINT" "12.413271,6.608202,0.003564")
(COMMAND "POINT" "12.465180,6.650436,0.004392")
(COMMAND "POINT" "12.516842,6.694342,0.005106")
(COMMAND "POINT" "12.568256,6.739919,0.005708")
(COMMAND "POINT" "12.619423,6.787168,0.006197")
(COMMAND "POINT" "12.670342,6.836089,0.006574")
(COMMAND "POINT" "12.721014,6.886681,0.006837")
(COMMAND "POINT" "12.771439,6.938945,0.006988")
(COMMAND "POINT" "12.821616,6.992881,0.007026")
(COMMAND "POINT" "12.871546,7.048488,0.006951")
(COMMAND "POINT" "12.921229,7.105766,0.006764")
(COMMAND "POINT" "12.970664,7.164717,0.006463")
(COMMAND "POINT" "13.019851,7.225339,0.006050")
(COMMAND "POINT" "13.068792,7.287633,0.005524")
(COMMAND "POINT" "13.117485,7.351598,0.004885")
(COMMAND "POINT" "13.165930,7.417235,0.004134")
(COMMAND "POINT" "13.214128,7.484543,0.003270")
(COMMAND "POINT" "13.262079,7.553523,0.002293")
(COMMAND "POINT" "13.309783,7.624175,0.001203")
(COMMAND "POINT" "13.357239,7.696499,0.000000")
(COMMAND "POINT" "2.757391,8.010148,-0.081407")
(COMMAND "POINT" "3.013283,7.948069,-0.084584")
(COMMAND "POINT" "3.265182,7.887149,-0.087618")
(COMMAND "POINT" "3.513089,7.827387,-0.090508")
(COMMAND "POINT" "3.757003,7.768783,-0.093256")
(COMMAND "POINT" "3.996924,7.711338,-0.095861")
(COMMAND "POINT" "4.232852,7.655050,-0.098323")
(COMMAND "POINT" "4.464788,7.599921,-0.100642")
(COMMAND "POINT" "4.692732,7.545949,-0.102819")
(COMMAND "POINT" "4.916682,7.493136,-0.104852")
(COMMAND "POINT" "5.136640,7.441481,-0.106742")
(COMMAND "POINT" "5.352605,7.390985,-0.108490")
(COMMAND "POINT" "5.564578,7.341646,-0.110095")
(COMMAND "POINT" "5.772558,7.293466,-0.111556")
(COMMAND "POINT" "5.976545,7.246443,-0.112875")
(COMMAND "POINT" "6.176540,7.200579,-0.114051")
(COMMAND "POINT" "6.372542,7.155873,-0.115084")
(COMMAND "POINT" "6.564551,7.112326,-0.115974")
(COMMAND "POINT" "6.752567,7.069936,-0.116722")
(COMMAND "POINT" "6.936591,7.028704,-0.117326")
(COMMAND "POINT" "7.116623,6.988631,-0.117787")
(COMMAND "POINT" "7.292661,6.949716,-0.118106")
(COMMAND "POINT" "7.464707,6.911959,-0.118281")
(COMMAND "POINT" "7.632761,6.875360,-0.118314")
(COMMAND "POINT" "7.796821,6.839919,-0.118204")
(COMMAND "POINT" "7.956889,6.805637,-0.117951")
(COMMAND "POINT" "8.112964,6.772512,-0.117555")
(COMMAND "POINT" "8.265047,6.740546,-0.117016")
(COMMAND "POINT" "8.413137,6.709738,-0.116334")
(COMMAND "POINT" "8.557234,6.680088,-0.115510")
(COMMAND "POINT" "8.697339,6.651596,-0.114542")
(COMMAND "POINT" "8.833451,6.624263,-0.113432")
(COMMAND "POINT" "8.965570,6.598087,-0.112178")
(COMMAND "POINT" "9.093697,6.573070,-0.110782")
(COMMAND "POINT" "9.217831,6.549211,-0.109243")
(COMMAND "POINT" "9.337972,6.526510,-0.107561")
(COMMAND "POINT" "9.454121,6.504967,-0.105736")
(COMMAND "POINT" "9.566277,6.484582,-0.103768")
(COMMAND "POINT" "9.674440,6.465356,-0.101657")
(COMMAND "POINT" "9.778611,6.447287,-0.099404")
(COMMAND "POINT" "9.878789,6.430377,-0.097007")
(COMMAND "POINT" "9.974974,6.414625,-0.094468")
(COMMAND "POINT" "10.067167,6.400031,-0.091785")
(COMMAND "POINT" "10.155367,6.386596,-0.088960")
(COMMAND "POINT" "10.239574,6.374318,-0.085992")
(COMMAND "POINT" "10.319789,6.363199,-0.082881")
(COMMAND "POINT" "10.396011,6.353237,-0.079627")
(COMMAND "POINT" "10.468241,6.344434,-0.076230")
(COMMAND "POINT" "10.536477,6.336789,-0.072690")
(COMMAND "POINT" "10.600721,6.330302,-0.069007")
(COMMAND "POINT" "10.661433,6.325032,-0.065212")
(COMMAND "POINT" "10.721371,6.321330,-0.061486")
(COMMAND "POINT" "10.780996,6.319255,-0.057860")
(COMMAND "POINT" "10.840308,6.318807,-0.054334")
(COMMAND "POINT" "10.899307,6.319985,-0.050908")
(COMMAND "POINT" "10.957993,6.322790,-0.047581")
(COMMAND "POINT" "11.016366,6.327222,-0.044354")
(COMMAND "POINT" "11.074426,6.333280,-0.041227")
(COMMAND "POINT" "11.132173,6.340966,-0.038200")
(COMMAND "POINT" "11.189607,6.350278,-0.035273")
(COMMAND "POINT" "11.246727,6.361216,-0.032445")
(COMMAND "POINT" "11.303535,6.373782,-0.029717")
(COMMAND "POINT" "11.360029,6.387974,-0.027089")
(COMMAND "POINT" "11.416210,6.403793,-0.024561")
(COMMAND "POINT" "11.472079,6.421238,-0.022132")
(COMMAND "POINT" "11.527634,6.440311,-0.019803")
(COMMAND "POINT" "11.582876,6.461010,-0.017574")
(COMMAND "POINT" "11.637805,6.483335,-0.015445")
(COMMAND "POINT" "11.692421,6.507288,-0.013416")
(COMMAND "POINT" "11.746724,6.532867,-0.011486")
(COMMAND "POINT" "11.800714,6.560073,-0.009656")
(COMMAND "POINT" "11.854390,6.588906,-0.007926")
(COMMAND "POINT" "11.907754,6.619365,-0.006296")
(COMMAND "POINT" "11.960805,6.651452,-0.004766")
(COMMAND "POINT" "12.013542,6.685165,-0.003335")
(COMMAND "POINT" "12.065967,6.720504,-0.002004")
(COMMAND "POINT" "12.118078,6.757471,-0.000773")
(COMMAND "POINT" "12.169876,6.796064,0.000358")
(COMMAND "POINT" "12.221361,6.836284,0.001390")
(COMMAND "POINT" "12.272533,6.878130,0.002321")
(COMMAND "POINT" "12.323392,6.921604,0.003153")
(COMMAND "POINT" "12.373938,6.966704,0.003885")
(COMMAND "POINT" "12.424171,7.013430,0.004518")
(COMMAND "POINT" "12.474091,7.061784,0.005050")
(COMMAND "POINT" "12.523698,7.111764,0.005483")
(COMMAND "POINT" "12.572991,7.163371,0.005816")
(COMMAND "POINT" "12.621972,7.216605,0.006049")
(COMMAND "POINT" "12.670639,7.271465,0.006183")
(COMMAND "POINT" "12.718993,7.327953,0.006216")
(COMMAND "POINT" "12.767035,7.386066,0.006150")
(COMMAND "POINT" "12.814763,7.445807,0.005984")
(COMMAND "POINT" "12.862178,7.507174,0.005718")
(COMMAND "POINT" "12.909280,7.570169,0.005353")
(COMMAND "POINT" "12.956069,7.634789,0.004888")
(COMMAND "POINT" "13.002545,7.701037,0.004322")
(COMMAND "POINT" "13.048708,7.768911,0.003657")
(COMMAND "POINT" "13.094558,7.838412,0.002893")
(COMMAND "POINT" "13.140094,7.909540,0.002028")
(COMMAND "POINT" "13.185318,7.982295,0.001064")
(COMMAND "POINT" "13.230228,8.056676,0.000000")
(COMMAND "POINT" "2.978261,8.345389,-0.069517")
(COMMAND "POINT" "3.221456,8.274173,-0.072229")
(COMMAND "POINT" "3.460933,8.204384,-0.074820")
(COMMAND "POINT" "3.696693,8.136021,-0.077288")
(COMMAND "POINT" "3.928734,8.069085,-0.079635")
(COMMAND "POINT" "4.157058,8.003575,-0.081859")
(COMMAND "POINT" "4.381664,7.939493,-0.083962")
(COMMAND "POINT" "4.602551,7.876836,-0.085942")
(COMMAND "POINT" "4.819721,7.815607,-0.087800")
(COMMAND "POINT" "5.033172,7.755804,-0.089537")
(COMMAND "POINT" "5.242906,7.697428,-0.091151")
(COMMAND "POINT" "5.448922,7.640478,-0.092643")
(COMMAND "POINT" "5.651220,7.584955,-0.094014")
(COMMAND "POINT" "5.849799,7.530859,-0.095262")
(COMMAND "POINT" "6.044661,7.478190,-0.096388")
(COMMAND "POINT" "6.235805,7.426947,-0.097392")
(COMMAND "POINT" "6.423231,7.377130,-0.098274")
(COMMAND "POINT" "6.606939,7.328741,-0.099034")
(COMMAND "POINT" "6.786929,7.281777,-0.099673")
(COMMAND "POINT" "6.963201,7.236241,-0.100189")
(COMMAND "POINT" "7.135755,7.192131,-0.100583")
(COMMAND "POINT" "7.304591,7.149448,-0.100855")
(COMMAND "POINT" "7.469709,7.108192,-0.101005")
(COMMAND "POINT" "7.631109,7.068362,-0.101033")
(COMMAND "POINT" "7.788791,7.029959,-0.100939")
(COMMAND "POINT" "7.942755,6.992982,-0.100722")
(COMMAND "POINT" "8.093001,6.957432,-0.100384")
(COMMAND "POINT" "8.239529,6.923309,-0.099924")
(COMMAND "POINT" "8.382339,6.890612,-0.099342")
(COMMAND "POINT" "8.521431,6.859342,-0.098638")
(COMMAND "POINT" "8.656806,6.829499,-0.097812")
(COMMAND "POINT" "8.788462,6.801082,-0.096863")
(COMMAND "POINT" "8.916400,6.774092,-0.095793")
(COMMAND "POINT" "9.040621,6.748529,-0.094601")
(COMMAND "POINT" "9.161123,6.724392,-0.093286")
(COMMAND "POINT" "9.277907,6.701682,-0.091850")
(COMMAND "POINT" "9.390974,6.680399,-0.090292")
(COMMAND "POINT" "9.500322,6.660542,-0.088611")
(COMMAND "POINT" "9.605953,6.642112,-0.086809")
(COMMAND "POINT" "9.707865,6.625108,-0.084884")
(COMMAND "POINT" "9.806060,6.609531,-0.082838")
(COMMAND "POINT" "9.900536,6.595381,-0.080669")
(COMMAND "POINT" "9.991295,6.582658,-0.078379")
(COMMAND "POINT" "10.078335,6.571361,-0.075966")
(COMMAND "POINT" "10.161658,6.561490,-0.073431")
(COMMAND "POINT" "10.241263,6.553047,-0.070775")
(COMMAND "POINT" "10.317149,6.546030,-0.067996")
(COMMAND "POINT" "10.389318,6.540439,-0.065095")
(COMMAND "POINT" "10.457769,6.536275,-0.062073")
(COMMAND "POINT" "10.522502,6.533538,-0.058928")
(COMMAND "POINT" "10.583934,6.532248,-0.055687")
(COMMAND "POINT" "10.644573,6.532522,-0.052505")
(COMMAND "POINT" "10.704836,6.534381,-0.049409")
(COMMAND "POINT" "10.764722,6.537824,-0.046398")
(COMMAND "POINT" "10.824233,6.542852,-0.043472")
(COMMAND "POINT" "10.883368,6.549464,-0.040631")
(COMMAND "POINT" "10.942126,6.557662,-0.037876")
(COMMAND "POINT" "11.000509,6.567443,-0.035205")
(COMMAND "POINT" "11.058516,6.578810,-0.032620")
(COMMAND "POINT" "11.116146,6.591761,-0.030121")
(COMMAND "POINT" "11.173401,6.606296,-0.027706")
(COMMAND "POINT" "11.230279,6.622416,-0.025376")
(COMMAND "POINT" "11.286782,6.640121,-0.023132")
(COMMAND "POINT" "11.342908,6.659410,-0.020973")
(COMMAND "POINT" "11.398659,6.680284,-0.018899")
(COMMAND "POINT" "11.454033,6.702743,-0.016911")
(COMMAND "POINT" "11.509032,6.726786,-0.015007")
(COMMAND "POINT" "11.563654,6.752414,-0.013189")
(COMMAND "POINT" "11.617901,6.779626,-0.011456")
(COMMAND "POINT" "11.671771,6.808423,-0.009808")
(COMMAND "POINT" "11.725265,6.838805,-0.008246")
(COMMAND "POINT" "11.778384,6.870771,-0.006769")
(COMMAND "POINT" "11.831126,6.904321,-0.005377")
(COMMAND "POINT" "11.883492,6.939457,-0.004070")
(COMMAND "POINT" "11.935483,6.976177,-0.002848")
(COMMAND "POINT" "11.987097,7.014481,-0.001711")
(COMMAND "POINT" "12.038335,7.054370,-0.000660")
(COMMAND "POINT" "12.089197,7.095844,0.000306")
(COMMAND "POINT" "12.139683,7.138902,0.001187")
(COMMAND "POINT" "12.189793,7.183545,0.001982")
(COMMAND "POINT" "12.239528,7.229773,0.002693")
(COMMAND "POINT" "12.288886,7.277585,0.003318")
(COMMAND "POINT" "12.337868,7.326982,0.003858")
(COMMAND "POINT" "12.386474,7.377963,0.004313")
(COMMAND "POINT" "12.434704,7.430529,0.004682")
(COMMAND "POINT" "12.482558,7.484679,0.004967")
(COMMAND "POINT" "12.530036,7.540415,0.005166")
(COMMAND "POINT" "12.577138,7.597734,0.005280")
(COMMAND "POINT" "12.623864,7.656639,0.005308")
(COMMAND "POINT" "12.670214,7.717127,0.005252")
(COMMAND "POINT" "12.716188,7.779201,0.005110")
(COMMAND "POINT" "12.761785,7.842859,0.004883")
(COMMAND "POINT" "12.807007,7.908102,0.004571")
(COMMAND "POINT" "12.851853,7.974929,0.004174")
(COMMAND "POINT" "12.896323,8.043341,0.003691")
(COMMAND "POINT" "12.940417,8.113337,0.003123")
(COMMAND "POINT" "12.984134,8.184919,0.002470")
(COMMAND "POINT" "13.027476,8.258084,0.001732")
(COMMAND "POINT" "13.070442,8.332835,0.000909")
(COMMAND "POINT" "13.113032,8.409169,0.000000")
(COMMAND "POINT" "3.187199,8.671064,-0.056340")
(COMMAND "POINT" "3.418167,8.591360,-0.058538")
(COMMAND "POINT" "3.645683,8.513332,-0.060638")
(COMMAND "POINT" "3.869749,8.436982,-0.062639")
(COMMAND "POINT" "4.090364,8.362308,-0.064540")
(COMMAND "POINT" "4.307527,8.289312,-0.066343")
(COMMAND "POINT" "4.521240,8.217992,-0.068047")
(COMMAND "POINT" "4.731501,8.148349,-0.069652")
(COMMAND "POINT" "4.938312,8.080384,-0.071158")
(COMMAND "POINT" "5.141671,8.014095,-0.072565")
(COMMAND "POINT" "5.341580,7.949484,-0.073874")
(COMMAND "POINT" "5.538037,7.886549,-0.075083")
(COMMAND "POINT" "5.731044,7.825291,-0.076194")
(COMMAND "POINT" "5.920599,7.765711,-0.077205")
(COMMAND "POINT" "6.106704,7.707807,-0.078118")
(COMMAND "POINT" "6.289357,7.651580,-0.078932")
(COMMAND "POINT" "6.468560,7.597031,-0.079647")
(COMMAND "POINT" "6.644311,7.544158,-0.080263")
(COMMAND "POINT" "6.816612,7.492962,-0.080780")
(COMMAND "POINT" "6.985461,7.443444,-0.081198")
(COMMAND "POINT" "7.150859,7.395602,-0.081518")
(COMMAND "POINT" "7.312807,7.349437,-0.081738")
(COMMAND "POINT" "7.471303,7.304950,-0.081860")
(COMMAND "POINT" "7.626349,7.262139,-0.081882")
(COMMAND "POINT" "7.777943,7.221005,-0.081806")
(COMMAND "POINT" "7.926087,7.181549,-0.081631")
(COMMAND "POINT" "8.070779,7.143769,-0.081357")
(COMMAND "POINT" "8.212020,7.107666,-0.080984")
(COMMAND "POINT" "8.349811,7.073240,-0.080512")
(COMMAND "POINT" "8.484150,7.040491,-0.079941")
(COMMAND "POINT" "8.615038,7.009420,-0.079272")
(COMMAND "POINT" "8.742476,6.980025,-0.078503")
(COMMAND "POINT" "8.866462,6.952307,-0.077636")
(COMMAND "POINT" "8.986997,6.926266,-0.076669")
(COMMAND "POINT" "9.104082,6.901902,-0.075604")
(COMMAND "POINT" "9.217715,6.879216,-0.074440")
(COMMAND "POINT" "9.327897,6.858206,-0.073177")
(COMMAND "POINT" "9.434629,6.838873,-0.071815")
(COMMAND "POINT" "9.537909,6.821217,-0.070354")
(COMMAND "POINT" "9.637738,6.805238,-0.068795")
(COMMAND "POINT" "9.734117,6.790936,-0.067136")
(COMMAND "POINT" "9.827044,6.778312,-0.065379")
(COMMAND "POINT" "9.916520,6.767364,-0.063522")
(COMMAND "POINT" "10.002545,6.758093,-0.061567")
(COMMAND "POINT" "10.085120,6.750499,-0.059513")
(COMMAND "POINT" "10.164243,6.744582,-0.057360")
(COMMAND "POINT" "10.239915,6.740342,-0.055108")
(COMMAND "POINT" "10.312136,6.737779,-0.052757")
(COMMAND "POINT" "10.380907,6.736893,-0.050307")
(COMMAND "POINT" "10.446226,6.737684,-0.047758")
(COMMAND "POINT" "10.508471,6.740136,-0.045132")
(COMMAND "POINT" "10.569903,6.744149,-0.042553")
(COMMAND "POINT" "10.630899,6.749708,-0.040044")
(COMMAND "POINT" "10.691458,6.756811,-0.037603")
(COMMAND "POINT" "10.751582,6.765460,-0.035232")
(COMMAND "POINT" "10.811269,6.775655,-0.032930")
(COMMAND "POINT" "10.870520,6.787394,-0.030697")
(COMMAND "POINT" "10.929334,6.800679,-0.028532")
(COMMAND "POINT" "10.987713,6.815509,-0.026437")
(COMMAND "POINT" "11.045655,6.831884,-0.024411")
(COMMAND "POINT" "11.103161,6.849804,-0.022454")
(COMMAND "POINT" "11.160231,6.869270,-0.020566")
(COMMAND "POINT" "11.216865,6.890281,-0.018748")
(COMMAND "POINT" "11.273062,6.912837,-0.016998")
(COMMAND "POINT" "11.328823,6.936938,-0.015317")
(COMMAND "POINT" "11.384148,6.962584,-0.013705")
(COMMAND "POINT" "11.439037,6.989776,-0.012163")
(COMMAND "POINT" "11.493490,7.018513,-0.010689")
(COMMAND "POINT" "11.547506,7.048795,-0.009285")
(COMMAND "POINT" "11.601086,7.080623,-0.007949")
(COMMAND "POINT" "11.654230,7.113996,-0.006683")
(COMMAND "POINT" "11.706938,7.148913,-0.005486")
(COMMAND "POINT" "11.759209,7.185377,-0.004357")
(COMMAND "POINT" "11.811044,7.223385,-0.003298")
(COMMAND "POINT" "11.862443,7.262939,-0.002308")
(COMMAND "POINT" "11.913406,7.304037,-0.001387")
(COMMAND "POINT" "11.963933,7.346682,-0.000535")
(COMMAND "POINT" "12.014023,7.390871,0.000248")
(COMMAND "POINT" "12.063677,7.436605,0.000962")
(COMMAND "POINT" "12.112895,7.483885,0.001607")
(COMMAND "POINT" "12.161677,7.532710,0.002182")
(COMMAND "POINT" "12.210022,7.583080,0.002689")
(COMMAND "POINT" "12.257932,7.634996,0.003127")
(COMMAND "POINT" "12.305405,7.688457,0.003495")
(COMMAND "POINT" "12.352442,7.743463,0.003795")
(COMMAND "POINT" "12.399042,7.800014,0.004025")
(COMMAND "POINT" "12.445207,7.858110,0.004187")
(COMMAND "POINT" "12.490935,7.917752,0.004279")
(COMMAND "POINT" "12.536227,7.978939,0.004302")
(COMMAND "POINT" "12.581083,8.041671,0.004256")
(COMMAND "POINT" "12.625502,8.105948,0.004141")
(COMMAND "POINT" "12.669486,8.171771,0.003958")
(COMMAND "POINT" "12.713033,8.239138,0.003705")
(COMMAND "POINT" "12.756144,8.308051,0.003383")
(COMMAND "POINT" "12.798819,8.378510,0.002991")
(COMMAND "POINT" "12.841057,8.450513,0.002531")
(COMMAND "POINT" "12.882859,8.524062,0.002002")
(COMMAND "POINT" "12.924225,8.599156,0.001404")
(COMMAND "POINT" "12.965155,8.675795,0.000736")
(COMMAND "POINT" "13.005649,8.753979,0.000000")
(COMMAND "POINT" "3.384207,8.987174,-0.041878")
(COMMAND "POINT" "3.603416,8.899630,-0.043512")
(COMMAND "POINT" "3.819432,8.813995,-0.045072")
(COMMAND "POINT" "4.032257,8.730270,-0.046559")
(COMMAND "POINT" "4.241890,8.648453,-0.047973")
(COMMAND "POINT" "4.448331,8.568546,-0.049313")
(COMMAND "POINT" "4.651581,8.490548,-0.050579")
(COMMAND "POINT" "4.851638,8.414460,-0.051772")
(COMMAND "POINT" "5.048504,8.340280,-0.052892")
(COMMAND "POINT" "5.242178,8.268010,-0.053938")
(COMMAND "POINT" "5.432661,8.197649,-0.054910")
(COMMAND "POINT" "5.619951,8.129197,-0.055809")
(COMMAND "POINT" "5.804050,8.062654,-0.056635")
(COMMAND "POINT" "5.984957,7.998021,-0.057387")
(COMMAND "POINT" "6.162673,7.935296,-0.058065")
(COMMAND "POINT" "6.337196,7.874481,-0.058670")
(COMMAND "POINT" "6.508528,7.815575,-0.059201")
(COMMAND "POINT" "6.676668,7.758578,-0.059659")
(COMMAND "POINT" "6.841616,7.703491,-0.060044")
(COMMAND "POINT" "7.003373,7.650313,-0.060355")
(COMMAND "POINT" "7.161937,7.599043,-0.060592")
(COMMAND "POINT" "7.317310,7.549684,-0.060756")
(COMMAND "POINT" "7.469492,7.502233,-0.060846")
(COMMAND "POINT" "7.618481,7.456691,-0.060863")
(COMMAND "POINT" "7.764279,7.413059,-0.060806")
(COMMAND "POINT" "7.906884,7.371336,-0.060676")
(COMMAND "POINT" "8.046299,7.331522,-0.060473")
(COMMAND "POINT" "8.182521,7.293617,-0.060195")
(COMMAND "POINT" "8.315551,7.257622,-0.059845")
(COMMAND "POINT" "8.445390,7.223535,-0.059420")
(COMMAND "POINT" "8.572037,7.191358,-0.058923")
(COMMAND "POINT" "8.695492,7.161090,-0.058351")
(COMMAND "POINT" "8.815756,7.132731,-0.057707")
(COMMAND "POINT" "8.932828,7.106282,-0.056988")
(COMMAND "POINT" "9.046708,7.081741,-0.056197")
(COMMAND "POINT" "9.157396,7.059110,-0.055331")
(COMMAND "POINT" "9.264892,7.038388,-0.054393")
(COMMAND "POINT" "9.369197,7.019576,-0.053380")
(COMMAND "POINT" "9.470310,7.002672,-0.052294")
(COMMAND "POINT" "9.568231,6.987678,-0.051135")
(COMMAND "POINT" "9.662960,6.974593,-0.049902")
(COMMAND "POINT" "9.754498,6.963417,-0.048596")
(COMMAND "POINT" "9.842843,6.954150,-0.047216")
(COMMAND "POINT" "9.927997,6.946792,-0.045763")
(COMMAND "POINT" "10.009960,6.941344,-0.044236")
(COMMAND "POINT" "10.088730,6.937805,-0.042635")
(COMMAND "POINT" "10.164309,6.936175,-0.040962")
(COMMAND "POINT" "10.236696,6.936454,-0.039214")
(COMMAND "POINT" "10.305891,6.938642,-0.037393")
(COMMAND "POINT" "10.371894,6.942740,-0.035499")
(COMMAND "POINT" "10.435043,6.948697,-0.033546")
(COMMAND "POINT" "10.497361,6.956212,-0.031630")
(COMMAND "POINT" "10.559185,6.965236,-0.029765")
(COMMAND "POINT" "10.620516,6.975769,-0.027951")
(COMMAND "POINT" "10.681353,6.987810,-0.026188")
(COMMAND "POINT" "10.741696,7.001360,-0.024477")
(COMMAND "POINT" "10.801546,7.016419,-0.022817")
(COMMAND "POINT" "10.860902,7.032986,-0.021208")
(COMMAND "POINT" "10.919764,7.051062,-0.019651")
(COMMAND "POINT" "10.978133,7.070647,-0.018145")
(COMMAND "POINT" "11.036008,7.091740,-0.016690")
(COMMAND "POINT" "11.093390,7.114342,-0.015287")
(COMMAND "POINT" "11.150277,7.138452,-0.013935")
(COMMAND "POINT" "11.206671,7.164071,-0.012634")
(COMMAND "POINT" "11.262572,7.191199,-0.011385")
(COMMAND "POINT" "11.317978,7.219835,-0.010187")
(COMMAND "POINT" "11.372892,7.249980,-0.009041")
(COMMAND "POINT" "11.427311,7.281634,-0.007945")
(COMMAND "POINT" "11.481237,7.314796,-0.006901")
(COMMAND "POINT" "11.534669,7.349467,-0.005909")
(COMMAND "POINT" "11.587607,7.385646,-0.004967")
(COMMAND "POINT" "11.640052,7.423334,-0.004077")
(COMMAND "POINT" "11.692003,7.462531,-0.003239")
(COMMAND "POINT" "11.743461,7.503236,-0.002452")
(COMMAND "POINT" "11.794424,7.545450,-0.001716")
(COMMAND "POINT" "11.844894,7.589173,-0.001031")
(COMMAND "POINT" "11.894871,7.634404,-0.000398")
(COMMAND "POINT" "11.944354,7.681144,0.000184")
(COMMAND "POINT" "11.993343,7.729393,0.000715")
(COMMAND "POINT" "12.041838,7.779150,0.001194")
(COMMAND "POINT" "12.089840,7.830416,0.001622")
(COMMAND "POINT" "12.137348,7.883190,0.001999")
(COMMAND "POINT" "12.184363,7.937473,0.002324")
(COMMAND "POINT" "12.230884,7.993265,0.002598")
(COMMAND "POINT" "12.276911,8.050565,0.002821")
(COMMAND "POINT" "12.322445,8.109374,0.002992")
(COMMAND "POINT" "12.367484,8.169692,0.003112")
(COMMAND "POINT" "12.412031,8.231518,0.003180")
(COMMAND "POINT" "12.456083,8.294853,0.003198")
(COMMAND "POINT" "12.499642,8.359696,0.003164")
(COMMAND "POINT" "12.542707,8.426048,0.003078")
(COMMAND "POINT" "12.585279,8.493909,0.002942")
(COMMAND "POINT" "12.627357,8.563279,0.002754")
(COMMAND "POINT" "12.668941,8.634157,0.002514")
(COMMAND "POINT" "12.710032,8.706543,0.002224")
(COMMAND "POINT" "12.750629,8.780439,0.001881")
(COMMAND "POINT" "12.790732,8.855842,0.001488")
(COMMAND "POINT" "12.830342,8.932755,0.001043")
(COMMAND "POINT" "12.869458,9.011176,0.000547")
(COMMAND "POINT" "12.908080,9.091106,0.000000")
(COMMAND "POINT" "3.569285,9.293717,-0.026129")
(COMMAND "POINT" "3.777202,9.198983,-0.027149")
(COMMAND "POINT" "3.982180,9.106372,-0.028122")
(COMMAND "POINT" "4.184217,9.015885,-0.029050")
(COMMAND "POINT" "4.383314,8.927520,-0.029932")
(COMMAND "POINT" "4.579470,8.841279,-0.030768")
(COMMAND "POINT" "4.772687,8.757162,-0.031559")
(COMMAND "POINT" "4.962963,8.675167,-0.032303")
(COMMAND "POINT" "5.150299,8.595296,-0.033001")
(COMMAND "POINT" "5.334694,8.517548,-0.033654")
(COMMAND "POINT" "5.516149,8.441923,-0.034261")
(COMMAND "POINT" "5.694664,8.368422,-0.034822")
(COMMAND "POINT" "5.870239,8.297043,-0.035337")
(COMMAND "POINT" "6.042874,8.227788,-0.035806")
(COMMAND "POINT" "6.212568,8.160657,-0.036229")
(COMMAND "POINT" "6.379322,8.095648,-0.036607")
(COMMAND "POINT" "6.543136,8.032763,-0.036938")
(COMMAND "POINT" "6.704010,7.972001,-0.037224")
(COMMAND "POINT" "6.861943,7.913363,-0.037464")
(COMMAND "POINT" "7.016936,7.856847,-0.037658")
(COMMAND "POINT" "7.168989,7.802455,-0.037806")
(COMMAND "POINT" "7.318101,7.750187,-0.037908")
(COMMAND "POINT" "7.464273,7.700041,-0.037965")
(COMMAND "POINT" "7.607505,7.652019,-0.037975")
(COMMAND "POINT" "7.747797,7.606120,-0.037940")
(COMMAND "POINT" "7.885149,7.562344,-0.037858")
(COMMAND "POINT" "8.019560,7.520691,-0.037731")
(COMMAND "POINT" "8.151031,7.481162,-0.037558")
(COMMAND "POINT" "8.279561,7.443756,-0.037340")
(COMMAND "POINT" "8.405152,7.408474,-0.037075")
(COMMAND "POINT" "8.527802,7.375314,-0.036764")
(COMMAND "POINT" "8.647512,7.344278,-0.036408")
(COMMAND "POINT" "8.764282,7.315365,-0.036006")
(COMMAND "POINT" "8.878111,7.288576,-0.035558")
(COMMAND "POINT" "8.989000,7.263909,-0.035063")
(COMMAND "POINT" "9.096949,7.241366,-0.034524")
(COMMAND "POINT" "9.201958,7.220946,-0.033938")
(COMMAND "POINT" "9.304026,7.202650,-0.033306")
(COMMAND "POINT" "9.403154,7.186476,-0.032629")
(COMMAND "POINT" "9.499342,7.172426,-0.031905")
(COMMAND "POINT" "9.592590,7.160500,-0.031136")
(COMMAND "POINT" "9.682897,7.150696,-0.030321")
(COMMAND "POINT" "9.770264,7.143016,-0.029460")
(COMMAND "POINT" "9.854691,7.137459,-0.028553")
(COMMAND "POINT" "9.936178,7.134025,-0.027601")
(COMMAND "POINT" "10.014724,7.132715,-0.026602")
(COMMAND "POINT" "10.090330,7.133528,-0.025558")
(COMMAND "POINT" "10.162996,7.136464,-0.024467")
(COMMAND "POINT" "10.232721,7.141523,-0.023331")
(COMMAND "POINT" "10.299507,7.148706,-0.022149")
(COMMAND "POINT" "10.363651,7.157930,-0.020931")
(COMMAND "POINT" "10.426947,7.168711,-0.019735")
(COMMAND "POINT" "10.489696,7.180967,-0.018571")
(COMMAND "POINT" "10.551896,7.194697,-0.017440")
(COMMAND "POINT" "10.613547,7.209902,-0.016340")
(COMMAND "POINT" "10.674651,7.226582,-0.015272")
(COMMAND "POINT" "10.735206,7.244737,-0.014236")
(COMMAND "POINT" "10.795212,7.264366,-0.013233")
(COMMAND "POINT" "10.854670,7.285470,-0.012261")
(COMMAND "POINT" "10.913580,7.308049,-0.011321")
(COMMAND "POINT" "10.971942,7.332103,-0.010414")
(COMMAND "POINT" "11.029755,7.357632,-0.009538")
(COMMAND "POINT" "11.087020,7.384636,-0.008695")
(COMMAND "POINT" "11.143736,7.413114,-0.007883")
(COMMAND "POINT" "11.199904,7.443067,-0.007104")
(COMMAND "POINT" "11.255524,7.474495,-0.006356")
(COMMAND "POINT" "11.310595,7.507397,-0.005641")
(COMMAND "POINT" "11.365118,7.541775,-0.004957")
(COMMAND "POINT" "11.419093,7.577627,-0.004306")
(COMMAND "POINT" "11.472519,7.614954,-0.003687")
(COMMAND "POINT" "11.525397,7.653756,-0.003099")
(COMMAND "POINT" "11.577727,7.694033,-0.002544")
(COMMAND "POINT" "11.629508,7.735784,-0.002021")
(COMMAND "POINT" "11.680741,7.779011,-0.001530")
(COMMAND "POINT" "11.731426,7.823712,-0.001070")
(COMMAND "POINT" "11.781562,7.869888,-0.000643")
(COMMAND "POINT" "11.831150,7.917538,-0.000248")
(COMMAND "POINT" "11.880189,7.966664,0.000115")
(COMMAND "POINT" "11.928680,8.017264,0.000446")
(COMMAND "POINT" "11.976623,8.069339,0.000745")
(COMMAND "POINT" "12.024018,8.122889,0.001012")
(COMMAND "POINT" "12.070864,8.177914,0.001247")
(COMMAND "POINT" "12.117162,8.234413,0.001450")
(COMMAND "POINT" "12.162911,8.292388,0.001621")
(COMMAND "POINT" "12.208112,8.351837,0.001760")
(COMMAND "POINT" "12.252765,8.412761,0.001867")
(COMMAND "POINT" "12.296869,8.475159,0.001942")
(COMMAND "POINT" "12.340425,8.539033,0.001984")
(COMMAND "POINT" "12.383433,8.604381,0.001995")
(COMMAND "POINT" "12.425892,8.671204,0.001974")
(COMMAND "POINT" "12.467803,8.739502,0.001921")
(COMMAND "POINT" "12.509165,8.809275,0.001835")
(COMMAND "POINT" "12.549979,8.880522,0.001718")
(COMMAND "POINT" "12.590245,8.953244,0.001569")
(COMMAND "POINT" "12.629963,9.027442,0.001387")
(COMMAND "POINT" "12.669132,9.103113,0.001174")
(COMMAND "POINT" "12.707753,9.180260,0.000928")
(COMMAND "POINT" "12.745825,9.258882,0.000651")
(COMMAND "POINT" "12.783349,9.338978,0.000342")
(COMMAND "POINT" "12.820325,9.420549,0.000000")
(COMMAND "POINT" "3.742431,9.590695,-0.009095")
(COMMAND "POINT" "3.939527,9.489420,-0.009450")
(COMMAND "POINT" "4.133926,9.390464,-0.009789")
(COMMAND "POINT" "4.325628,9.293827,-0.010112")
(COMMAND "POINT" "4.514635,9.199509,-0.010419")
(COMMAND "POINT" "4.700944,9.107511,-0.010710")
(COMMAND "POINT" "4.884557,9.017832,-0.010985")
(COMMAND "POINT" "5.065474,8.930472,-0.011244")
(COMMAND "POINT" "5.243694,8.845431,-0.011487")
(COMMAND "POINT" "5.419218,8.762709,-0.011714")
(COMMAND "POINT" "5.592046,8.682307,-0.011925")
(COMMAND "POINT" "5.762176,8.604223,-0.012121")
(COMMAND "POINT" "5.929611,8.528459,-0.012300")
(COMMAND "POINT" "6.094349,8.455014,-0.012463")
(COMMAND "POINT" "6.256390,8.383889,-0.012611")
(COMMAND "POINT" "6.415735,8.315082,-0.012742")
(COMMAND "POINT" "6.572384,8.248595,-0.012857")
(COMMAND "POINT" "6.726336,8.184427,-0.012957")
(COMMAND "POINT" "6.877591,8.122578,-0.013040")
(COMMAND "POINT" "7.026150,8.063048,-0.013108")
(COMMAND "POINT" "7.172013,8.005838,-0.013159")
(COMMAND "POINT" "7.315179,7.950946,-0.013195")
(COMMAND "POINT" "7.455649,7.898374,-0.013215")
(COMMAND "POINT" "7.593422,7.848121,-0.013218")
(COMMAND "POINT" "7.728498,7.800188,-0.013206")
(COMMAND "POINT" "7.860879,7.754573,-0.013178")
(COMMAND "POINT" "7.990562,7.711278,-0.013133")
(COMMAND "POINT" "8.117550,7.670301,-0.013073")
(COMMAND "POINT" "8.241841,7.631644,-0.012997")
(COMMAND "POINT" "8.363435,7.595307,-0.012905")
(COMMAND "POINT" "8.482333,7.561288,-0.012797")
(COMMAND "POINT" "8.598534,7.529589,-0.012673")
(COMMAND "POINT" "8.712039,7.500208,-0.012533")
(COMMAND "POINT" "8.822848,7.473147,-0.012377")
(COMMAND "POINT" "8.930960,7.448406,-0.012205")
(COMMAND "POINT" "9.036375,7.425983,-0.012017")
(COMMAND "POINT" "9.139094,7.405879,-0.011813")
(COMMAND "POINT" "9.239117,7.388095,-0.011593")
(COMMAND "POINT" "9.336443,7.372630,-0.011357")
(COMMAND "POINT" "9.431073,7.359484,-0.011106")
(COMMAND "POINT" "9.523006,7.348658,-0.010838")
(COMMAND "POINT" "9.612243,7.340150,-0.010554")
(COMMAND "POINT" "9.698783,7.333962,-0.010254")
(COMMAND "POINT" "9.782627,7.330093,-0.009939")
(COMMAND "POINT" "9.863774,7.328543,-0.009607")
(COMMAND "POINT" "9.942225,7.329312,-0.009260")
(COMMAND "POINT" "10.017979,7.332401,-0.008896")
(COMMAND "POINT" "10.091037,7.337808,-0.008517")
(COMMAND "POINT" "10.161398,7.345535,-0.008121")
(COMMAND "POINT" "10.229063,7.355581,-0.007710")
(COMMAND "POINT" "10.294294,7.367837,-0.007286")
(COMMAND "POINT" "10.358662,7.381646,-0.006869")
(COMMAND "POINT" "10.422430,7.396899,-0.006464")
(COMMAND "POINT" "10.485597,7.413595,-0.006070")
(COMMAND "POINT" "10.548165,7.431735,-0.005688")
(COMMAND "POINT" "10.610132,7.451319,-0.005316")
(COMMAND "POINT" "10.671498,7.472347,-0.004955")
(COMMAND "POINT" "10.732265,7.494818,-0.004606")
(COMMAND "POINT" "10.792431,7.518733,-0.004268")
(COMMAND "POINT" "10.851996,7.544092,-0.003941")
(COMMAND "POINT" "10.910962,7.570895,-0.003625")
(COMMAND "POINT" "10.969327,7.599141,-0.003320")
(COMMAND "POINT" "11.027092,7.628831,-0.003026")
(COMMAND "POINT" "11.084257,7.659965,-0.002744")
(COMMAND "POINT" "11.140821,7.692542,-0.002473")
(COMMAND "POINT" "11.196785,7.726564,-0.002212")
(COMMAND "POINT" "11.252149,7.762029,-0.001963")
(COMMAND "POINT" "11.306912,7.798937,-0.001726")
(COMMAND "POINT" "11.361075,7.837290,-0.001499")
(COMMAND "POINT" "11.414638,7.877086,-0.001283")
(COMMAND "POINT" "11.467600,7.918326,-0.001079")
(COMMAND "POINT" "11.519963,7.961010,-0.000886")
(COMMAND "POINT" "11.571725,8.005137,-0.000703")
(COMMAND "POINT" "11.622886,8.050708,-0.000532")
(COMMAND "POINT" "11.673448,8.097723,-0.000373")
(COMMAND "POINT" "11.723409,8.146182,-0.000224")
(COMMAND "POINT" "11.772769,8.196084,-0.000086")
(COMMAND "POINT" "11.821530,8.247430,0.000040")
(COMMAND "POINT" "11.869690,8.300220,0.000155")
(COMMAND "POINT" "11.917250,8.354453,0.000259")
(COMMAND "POINT" "11.964209,8.410131,0.000352")
(COMMAND "POINT" "12.010568,8.467252,0.000434")
(COMMAND "POINT" "12.056327,8.525816,0.000505")
(COMMAND "POINT" "12.101486,8.585825,0.000564")
(COMMAND "POINT" "12.146044,8.647277,0.000613")
(COMMAND "POINT" "12.190002,8.710173,0.000650")
(COMMAND "POINT" "12.233360,8.774513,0.000676")
(COMMAND "POINT" "12.276118,8.840296,0.000691")
(COMMAND "POINT" "12.318275,8.907523,0.000694")
(COMMAND "POINT" "12.359832,8.976194,0.000687")
(COMMAND "POINT" "12.400788,9.046309,0.000669")
(COMMAND "POINT" "12.441144,9.117867,0.000639")
(COMMAND "POINT" "12.480900,9.190869,0.000598")
(COMMAND "POINT" "12.520056,9.265315,0.000546")
(COMMAND "POINT" "12.558611,9.341205,0.000483")
(COMMAND "POINT" "12.596566,9.418538,0.000409")
(COMMAND "POINT" "12.633921,9.497315,0.000323")
(COMMAND "POINT" "12.670676,9.577536,0.000227")
(COMMAND "POINT" "12.706830,9.659200,0.000119")
(COMMAND "POINT" "12.742384,9.742309,0.000000")
(COMMAND "POINT" "3.903647,9.878106,0.009225")
(COMMAND "POINT" "4.090389,9.770939,0.009585")
(COMMAND "POINT" "4.274671,9.666269,0.009929")
(COMMAND "POINT" "4.456492,9.564096,0.010256")
(COMMAND "POINT" "4.635853,9.464420,0.010568")
(COMMAND "POINT" "4.812753,9.367241,0.010863")
(COMMAND "POINT" "4.987193,9.272559,0.011142")
(COMMAND "POINT" "5.159173,9.180373,0.011405")
(COMMAND "POINT" "5.328692,9.090685,0.011651")
(COMMAND "POINT" "5.495751,9.003494,0.011882")
(COMMAND "POINT" "5.660349,8.918800,0.012096")
(COMMAND "POINT" "5.822487,8.836602,0.012294")
(COMMAND "POINT" "5.982165,8.756902,0.012476")
(COMMAND "POINT" "6.139382,8.679699,0.012642")
(COMMAND "POINT" "6.294138,8.604992,0.012791")
(COMMAND "POINT" "6.446435,8.532783,0.012924")
(COMMAND "POINT" "6.596271,8.463071,0.013041")
(COMMAND "POINT" "6.743646,8.395855,0.013142")
(COMMAND "POINT" "6.888561,8.331137,0.013227")
(COMMAND "POINT" "7.031016,8.268915,0.013295")
(COMMAND "POINT" "7.171010,8.209191,0.013348")
(COMMAND "POINT" "7.308544,8.151963,0.013384")
(COMMAND "POINT" "7.443617,8.097233,0.013404")
(COMMAND "POINT" "7.576230,8.044999,0.013407")
(COMMAND "POINT" "7.706383,7.995263,0.013395")
(COMMAND "POINT" "7.834075,7.948023,0.013366")
(COMMAND "POINT" "7.959307,7.903280,0.013321")
(COMMAND "POINT" "8.082078,7.861035,0.013260")
(COMMAND "POINT" "8.202389,7.821286,0.013183")
(COMMAND "POINT" "8.320240,7.784034,0.013090")
(COMMAND "POINT" "8.435630,7.749280,0.012980")
(COMMAND "POINT" "8.548559,7.717022,0.012854")
(COMMAND "POINT" "8.659029,7.687261,0.012712")
(COMMAND "POINT" "8.767038,7.659998,0.012554")
(COMMAND "POINT" "8.872586,7.635231,0.012379")
(COMMAND "POINT" "8.975674,7.612961,0.012189")
(COMMAND "POINT" "9.076302,7.593188,0.011982")
(COMMAND "POINT" "9.174469,7.575912,0.011759")
(COMMAND "POINT" "9.270176,7.561133,0.011520")
(COMMAND "POINT" "9.363422,7.548852,0.011264")
(COMMAND "POINT" "9.454208,7.539067,0.010993")
(COMMAND "POINT" "9.542534,7.531779,0.010705")
(COMMAND "POINT" "9.628399,7.526988,0.010401")
(COMMAND "POINT" "9.711804,7.524694,0.010081")
(COMMAND "POINT" "9.792748,7.524897,0.009745")
(COMMAND "POINT" "9.871232,7.527597,0.009392")
(COMMAND "POINT" "9.947256,7.532794,0.009023")
(COMMAND "POINT" "10.020819,7.540488,0.008638")
(COMMAND "POINT" "10.091921,7.550679,0.008237")
(COMMAND "POINT" "10.160564,7.563367,0.007820")
(COMMAND "POINT" "10.226972,7.578416,0.007390")
(COMMAND "POINT" "10.292504,7.595017,0.006968")
(COMMAND "POINT" "10.357387,7.613032,0.006557")
(COMMAND "POINT" "10.421621,7.632463,0.006157")
(COMMAND "POINT" "10.485205,7.653310,0.005769")
(COMMAND "POINT" "10.548139,7.675572,0.005392")
(COMMAND "POINT" "10.610424,7.699250,0.005026")
(COMMAND "POINT" "10.672059,7.724343,0.004672")
(COMMAND "POINT" "10.733045,7.750851,0.004329")
(COMMAND "POINT" "10.793382,7.778775,0.003997")
(COMMAND "POINT" "10.853069,7.808114,0.003677")
(COMMAND "POINT" "10.912106,7.838869,0.003368")
(COMMAND "POINT" "10.970494,7.871039,0.003070")
(COMMAND "POINT" "11.028233,7.904624,0.002783")
(COMMAND "POINT" "11.085322,7.939625,0.002508")
(COMMAND "POINT" "11.141761,7.976042,0.002244")
(COMMAND "POINT" "11.197551,8.013874,0.001992")
(COMMAND "POINT" "11.252692,8.053121,0.001750")
(COMMAND "POINT" "11.307183,8.093784,0.001520")
(COMMAND "POINT" "11.361024,8.135862,0.001302")
(COMMAND "POINT" "11.414216,8.179355,0.001094")
(COMMAND "POINT" "11.466759,8.224264,0.000898")
(COMMAND "POINT" "11.518652,8.270589,0.000713")
(COMMAND "POINT" "11.569896,8.318329,0.000540")
(COMMAND "POINT" "11.620490,8.367484,0.000378")
(COMMAND "POINT" "11.670434,8.418055,0.000227")
(COMMAND "POINT" "11.719729,8.470041,0.000088")
(COMMAND "POINT" "11.768375,8.523443,-0.000041")
(COMMAND "POINT" "11.816371,8.578260,-0.000157")
(COMMAND "POINT" "11.863718,8.634492,-0.000263")
(COMMAND "POINT" "11.910415,8.692140,-0.000357")
(COMMAND "POINT" "11.956462,8.751204,-0.000440")
(COMMAND "POINT" "12.001861,8.811683,-0.000512")
(COMMAND "POINT" "12.046609,8.873577,-0.000572")
(COMMAND "POINT" "12.090708,8.936887,-0.000621")
(COMMAND "POINT" "12.134158,9.001612,-0.000659")
(COMMAND "POINT" "12.176958,9.067752,-0.000685")
(COMMAND "POINT" "12.219109,9.135308,-0.000701")
(COMMAND "POINT" "12.260610,9.204280,-0.000704")
(COMMAND "POINT" "12.301462,9.274667,-0.000697")
(COMMAND "POINT" "12.341664,9.346469,-0.000678")
(COMMAND "POINT" "12.381217,9.419687,-0.000648")
(COMMAND "POINT" "12.420120,9.494320,-0.000607")
(COMMAND "POINT" "12.458374,9.570369,-0.000554")
(COMMAND "POINT" "12.495978,9.647833,-0.000490")
(COMMAND "POINT" "12.532932,9.726712,-0.000414")
(COMMAND "POINT" "12.569238,9.807007,-0.000328")
(COMMAND "POINT" "12.604893,9.888717,-0.000230")
(COMMAND "POINT" "12.639900,9.971843,-0.000121")
(COMMAND "POINT" "12.674256,10.056384,0.000000")
(COMMAND "POINT" "4.052932,10.155952,0.028831")
(COMMAND "POINT" "4.229790,10.043542,0.029956")
(COMMAND "POINT" "4.404415,9.933789,0.031030")
(COMMAND "POINT" "4.576808,9.826692,0.032054")
(COMMAND "POINT" "4.746968,9.722252,0.033027")
(COMMAND "POINT" "4.914897,9.620469,0.033950")
(COMMAND "POINT" "5.080594,9.521342,0.034822")
(COMMAND "POINT" "5.244059,9.424872,0.035643")
(COMMAND "POINT" "5.405291,9.331059,0.036414")
(COMMAND "POINT" "5.564292,9.239902,0.037134")
(COMMAND "POINT" "5.721060,9.151402,0.037804")
(COMMAND "POINT" "5.875597,9.065558,0.038422")
(COMMAND "POINT" "6.027901,8.982371,0.038991")
(COMMAND "POINT" "6.177973,8.901841,0.039508")
(COMMAND "POINT" "6.325813,8.823967,0.039975")
(COMMAND "POINT" "6.471421,8.748750,0.040392")
(COMMAND "POINT" "6.614797,8.676190,0.040758")
(COMMAND "POINT" "6.755941,8.606286,0.041073")
(COMMAND "POINT" "6.894853,8.539039,0.041338")
(COMMAND "POINT" "7.031533,8.474448,0.041552")
(COMMAND "POINT" "7.165980,8.412514,0.041715")
(COMMAND "POINT" "7.298196,8.353237,0.041828")
(COMMAND "POINT" "7.428179,8.296616,0.041890")
(COMMAND "POINT" "7.555931,8.242652,0.041902")
(COMMAND "POINT" "7.681450,8.191345,0.041863")
(COMMAND "POINT" "7.804737,8.142694,0.041773")
(COMMAND "POINT" "7.925793,8.096700,0.041633")
(COMMAND "POINT" "8.044616,8.053362,0.041442")
(COMMAND "POINT" "8.161207,8.012681,0.041201")
(COMMAND "POINT" "8.275566,7.974657,0.040909")
(COMMAND "POINT" "8.387693,7.939289,0.040566")
(COMMAND "POINT" "8.497587,7.906578,0.040173")
(COMMAND "POINT" "8.605250,7.876524,0.039729")
(COMMAND "POINT" "8.710681,7.849126,0.039234")
(COMMAND "POINT" "8.813879,7.824385,0.038689")
(COMMAND "POINT" "8.914846,7.802300,0.038093")
(COMMAND "POINT" "9.013580,7.782872,0.037447")
(COMMAND "POINT" "9.110083,7.766101,0.036750")
(COMMAND "POINT" "9.204353,7.751986,0.036003")
(COMMAND "POINT" "9.296391,7.740528,0.035204")
(COMMAND "POINT" "9.386197,7.731727,0.034356")
(COMMAND "POINT" "9.473771,7.725582,0.033456")
(COMMAND "POINT" "9.559113,7.722094,0.032506")
(COMMAND "POINT" "9.642223,7.721262,0.031506")
(COMMAND "POINT" "9.723101,7.723087,0.030455")
(COMMAND "POINT" "9.801746,7.727569,0.029353")
(COMMAND "POINT" "9.878160,7.734707,0.028200")
(COMMAND "POINT" "9.952342,7.744502,0.026997")
(COMMAND "POINT" "10.024291,7.756954,0.025744")
(COMMAND "POINT" "10.094008,7.772062,0.024439")
(COMMAND "POINT" "10.161686,7.789668,0.023095")
(COMMAND "POINT" "10.228475,7.808823,0.021776")
(COMMAND "POINT" "10.294569,7.829368,0.020492")
(COMMAND "POINT" "10.359966,7.851302,0.019243")
(COMMAND "POINT" "10.424668,7.874627,0.018029")
(COMMAND "POINT" "10.488673,7.899341,0.016851")
(COMMAND "POINT" "10.551983,7.925445,0.015708")
(COMMAND "POINT" "10.614597,7.952939,0.014601")
(COMMAND "POINT" "10.676514,7.981823,0.013529")
(COMMAND "POINT" "10.737736,8.012097,0.012492")
(COMMAND "POINT" "10.798262,8.043761,0.011491")
(COMMAND "POINT" "10.858092,8.076815,0.010524")
(COMMAND "POINT" "10.917226,8.111259,0.009594")
(COMMAND "POINT" "10.975664,8.147092,0.008698")
(COMMAND "POINT" "11.033407,8.184316,0.007838")
(COMMAND "POINT" "11.090453,8.222929,0.007013")
(COMMAND "POINT" "11.146803,8.262932,0.006224")
(COMMAND "POINT" "11.202458,8.304325,0.005470")
(COMMAND "POINT" "11.257416,8.347109,0.004751")
(COMMAND "POINT" "11.311679,8.391282,0.004068")
(COMMAND "POINT" "11.365245,8.436844,0.003420")
(COMMAND "POINT" "11.418116,8.483797,0.002807")
(COMMAND "POINT" "11.470290,8.532140,0.002230")
(COMMAND "POINT" "11.521769,8.581873,0.001688")
(COMMAND "POINT" "11.572552,8.632995,0.001181")
(COMMAND "POINT" "11.622639,8.685507,0.000710")
(COMMAND "POINT" "11.672030,8.739410,0.000274")
(COMMAND "POINT" "11.720725,8.794702,-0.000127")
(COMMAND "POINT" "11.768724,8.851384,-0.000492")
(COMMAND "POINT" "11.816027,8.909456,-0.000822")
(COMMAND "POINT" "11.862634,8.968918,-0.001117")
(COMMAND "POINT" "11.908546,9.029770,-0.001376")
(COMMAND "POINT" "11.953761,9.092012,-0.001600")
(COMMAND "POINT" "11.998280,9.155643,-0.001789")
(COMMAND "POINT" "12.042104,9.220665,-0.001942")
(COMMAND "POINT" "12.085231,9.287076,-0.002060")
(COMMAND "POINT" "12.127663,9.354878,-0.002142")
(COMMAND "POINT" "12.169398,9.424069,-0.002190")
(COMMAND "POINT" "12.210438,9.494650,-0.002202")
(COMMAND "POINT" "12.250782,9.566621,-0.002178")
(COMMAND "POINT" "12.290430,9.639982,-0.002119")
(COMMAND "POINT" "12.329382,9.714733,-0.002025")
(COMMAND "POINT" "12.367638,9.790874,-0.001896")
(COMMAND "POINT" "12.405198,9.868405,-0.001731")
(COMMAND "POINT" "12.442062,9.947325,-0.001531")
(COMMAND "POINT" "12.478230,10.027636,-0.001295")
(COMMAND "POINT" "12.513702,10.109336,-0.001025")
(COMMAND "POINT" "12.548478,10.192427,-0.000718")
(COMMAND "POINT" "12.582559,10.276907,-0.000377")
(COMMAND "POINT" "12.615943,10.362777,0.000000")
(COMMAND "POINT" "4.190287,10.424232,0.049723")
(COMMAND "POINT" "4.357728,10.307228,0.051663")
(COMMAND "POINT" "4.523157,10.193023,0.053516")
(COMMAND "POINT" "4.686575,10.081616,0.055281")
(COMMAND "POINT" "4.847981,9.973007,0.056960")
(COMMAND "POINT" "5.007376,9.867196,0.058551")
(COMMAND "POINT" "5.164760,9.764183,0.060055")
(COMMAND "POINT" "5.320132,9.663968,0.061471")
(COMMAND "POINT" "5.473492,9.566552,0.062800")
(COMMAND "POINT" "5.624841,9.471934,0.064042")
(COMMAND "POINT" "5.774179,9.380113,0.065197")
(COMMAND "POINT" "5.921505,9.291091,0.066264")
(COMMAND "POINT" "6.066820,9.204867,0.067245")
(COMMAND "POINT" "6.210123,9.121441,0.068137")
(COMMAND "POINT" "6.351414,9.040814,0.068943")
(COMMAND "POINT" "6.490695,8.962984,0.069661")
(COMMAND "POINT" "6.627963,8.887953,0.070292")
(COMMAND "POINT" "6.763221,8.815719,0.070836")
(COMMAND "POINT" "6.896467,8.746284,0.071292")
(COMMAND "POINT" "7.027701,8.679647,0.071661")
(COMMAND "POINT" "7.156924,8.615808,0.071943")
(COMMAND "POINT" "7.284135,8.554768,0.072138")
(COMMAND "POINT" "7.409335,8.496525,0.072245")
(COMMAND "POINT" "7.532524,8.441080,0.072265")
(COMMAND "POINT" "7.653701,8.388434,0.072198")
(COMMAND "POINT" "7.772866,8.338586,0.072043")
(COMMAND "POINT" "7.890020,8.291536,0.071801")
(COMMAND "POINT" "8.005163,8.247284,0.071472")
(COMMAND "POINT" "8.118294,8.205830,0.071056")
(COMMAND "POINT" "8.229413,8.167174,0.070552")
(COMMAND "POINT" "8.338522,8.131316,0.069961")
(COMMAND "POINT" "8.445618,8.098257,0.069283")
(COMMAND "POINT" "8.550703,8.067996,0.068517")
(COMMAND "POINT" "8.653777,8.040532,0.067664")
(COMMAND "POINT" "8.754839,8.015867,0.066724")
(COMMAND "POINT" "8.853890,7.994000,0.065697")
(COMMAND "POINT" "8.950930,7.974932,0.064582")
(COMMAND "POINT" "9.045957,7.958661,0.063380")
(COMMAND "POINT" "9.138974,7.945188,0.062091")
(COMMAND "POINT" "9.229979,7.934514,0.060715")
(COMMAND "POINT" "9.318972,7.926638,0.059251")
(COMMAND "POINT" "9.405954,7.921560,0.057700")
(COMMAND "POINT" "9.490925,7.919280,0.056061")
(COMMAND "POINT" "9.573884,7.919798,0.054336")
(COMMAND "POINT" "9.654831,7.923114,0.052523")
(COMMAND "POINT" "9.733767,7.929228,0.050623")
(COMMAND "POINT" "9.810692,7.938141,0.048635")
(COMMAND "POINT" "9.885605,7.949851,0.046560")
(COMMAND "POINT" "9.958507,7.964360,0.044398")
(COMMAND "POINT" "10.029397,7.981667,0.042149")
(COMMAND "POINT" "10.098435,8.001593,0.039831")
(COMMAND "POINT" "10.166574,8.023065,0.037555")
(COMMAND "POINT" "10.233973,8.045905,0.035341")
(COMMAND "POINT" "10.300633,8.070111,0.033187")
(COMMAND "POINT" "10.366553,8.095685,0.031094")
(COMMAND "POINT" "10.431734,8.122625,0.029062")
(COMMAND "POINT" "10.496175,8.150933,0.027091")
(COMMAND "POINT" "10.559876,8.180608,0.025181")
(COMMAND "POINT" "10.622838,8.211650,0.023332")
(COMMAND "POINT" "10.685060,8.244060,0.021544")
(COMMAND "POINT" "10.746542,8.277836,0.019817")
(COMMAND "POINT" "10.807285,8.312980,0.018151")
(COMMAND "POINT" "10.867288,8.349490,0.016546")
(COMMAND "POINT" "10.926552,8.387368,0.015001")
(COMMAND "POINT" "10.985076,8.426613,0.013518")
(COMMAND "POINT" "11.042860,8.467225,0.012096")
(COMMAND "POINT" "11.099905,8.509205,0.010734")
(COMMAND "POINT" "11.156210,8.552551,0.009434")
(COMMAND "POINT" "11.211775,8.597265,0.008194")
(COMMAND "POINT" "11.266601,8.643345,0.007016")
(COMMAND "POINT" "11.320687,8.690793,0.005898")
(COMMAND "POINT" "11.374033,8.739608,0.004841")
(COMMAND "POINT" "11.426640,8.789790,0.003846")
(COMMAND "POINT" "11.478507,8.841339,0.002911")
(COMMAND "POINT" "11.529635,8.894256,0.002037")
(COMMAND "POINT" "11.580023,8.948539,0.001224")
(COMMAND "POINT" "11.629671,9.004190,0.000472")
(COMMAND "POINT" "11.678580,9.061208,-0.000219")
(COMMAND "POINT" "11.726749,9.119593,-0.000849")
(COMMAND "POINT" "11.774178,9.179345,-0.001418")
(COMMAND "POINT" "11.820868,9.240464,-0.001926")
(COMMAND "POINT" "11.866818,9.302950,-0.002373")
(COMMAND "POINT" "11.912029,9.366804,-0.002759")
(COMMAND "POINT" "11.956499,9.432024,-0.003085")
(COMMAND "POINT" "12.000231,9.498612,-0.003349")
(COMMAND "POINT" "12.043222,9.566567,-0.003552")
(COMMAND "POINT" "12.085474,9.635889,-0.003695")
(COMMAND "POINT" "12.126987,9.706578,-0.003776")
(COMMAND "POINT" "12.167759,9.778635,-0.003797")
(COMMAND "POINT" "12.207792,9.852058,-0.003756")
(COMMAND "POINT" "12.247086,9.926849,-0.003655")
(COMMAND "POINT" "12.285640,10.003007,-0.003493")
(COMMAND "POINT" "12.323454,10.080532,-0.003269")
(COMMAND "POINT" "12.360528,10.159424,-0.002985")
(COMMAND "POINT" "12.396863,10.239683,-0.002640")
(COMMAND "POINT" "12.432459,10.321309,-0.002234")
(COMMAND "POINT" "12.467314,10.404303,-0.001767")
(COMMAND "POINT" "12.501430,10.488663,-0.001239")
(COMMAND "POINT" "12.534807,10.574391,-0.000650")
(COMMAND "POINT" "12.567444,10.661486,0.000000")
(COMMAND "POINT" "4.315711,10.682945,0.071900")
(COMMAND "POINT" "4.474204,10.561997,0.074706")
(COMMAND "POINT" "4.630898,10.443971,0.077385")
(COMMAND "POINT" "4.785794,10.328866,0.079938")
(COMMAND "POINT" "4.938892,10.216683,0.082365")
(COMMAND "POINT" "5.090190,10.107421,0.084666")
(COMMAND "POINT" "5.239690,10.001081,0.086841")
(COMMAND "POINT" "5.387392,9.897662,0.088889")
(COMMAND "POINT" "5.533295,9.797164,0.090811")
(COMMAND "POINT" "5.677399,9.699589,0.092607")
(COMMAND "POINT" "5.819705,9.604934,0.094277")
(COMMAND "POINT" "5.960212,9.513201,0.095820")
(COMMAND "POINT" "6.098921,9.424390,0.097237")
(COMMAND "POINT" "6.235831,9.338500,0.098528")
(COMMAND "POINT" "6.370942,9.255532,0.099693")
(COMMAND "POINT" "6.504255,9.175485,0.100732")
(COMMAND "POINT" "6.635769,9.098360,0.101644")
(COMMAND "POINT" "6.765485,9.024156,0.102430")
(COMMAND "POINT" "6.893402,8.952873,0.103090")
(COMMAND "POINT" "7.019520,8.884512,0.103624")
(COMMAND "POINT" "7.143840,8.819073,0.104032")
(COMMAND "POINT" "7.266362,8.756555,0.104313")
(COMMAND "POINT" "7.387084,8.696959,0.104468")
(COMMAND "POINT" "7.506008,8.640284,0.104497")
(COMMAND "POINT" "7.623134,8.586530,0.104400")
(COMMAND "POINT" "7.738461,8.535699,0.104176")
(COMMAND "POINT" "7.851989,8.487788,0.103826")
(COMMAND "POINT" "7.963719,8.442799,0.103351")
(COMMAND "POINT" "8.073650,8.400732,0.102748")
(COMMAND "POINT" "8.181783,8.361586,0.102020")
(COMMAND "POINT" "8.288116,8.325361,0.101166")
(COMMAND "POINT" "8.392652,8.292059,0.100185")
(COMMAND "POINT" "8.495389,8.261677,0.099078")
(COMMAND "POINT" "8.596327,8.234217,0.097845")
(COMMAND "POINT" "8.695466,8.209679,0.096485")
(COMMAND "POINT" "8.792807,8.188062,0.094999")
(COMMAND "POINT" "8.888350,8.169366,0.093388")
(COMMAND "POINT" "8.982094,8.153592,0.091650")
(COMMAND "POINT" "9.074039,8.140740,0.089785")
(COMMAND "POINT" "9.164186,8.130809,0.087795")
(COMMAND "POINT" "9.252534,8.123800,0.085678")
(COMMAND "POINT" "9.339083,8.119712,0.083435")
(COMMAND "POINT" "9.423834,8.118545,0.081066")
(COMMAND "POINT" "9.506786,8.120300,0.078571")
(COMMAND "POINT" "9.587940,8.124977,0.075949")
(COMMAND "POINT" "9.667295,8.132575,0.073202")
(COMMAND "POINT" "9.744852,8.143094,0.070328")
(COMMAND "POINT" "9.820610,8.156535,0.067327")
(COMMAND "POINT" "9.894569,8.172898,0.064201")
(COMMAND "POINT" "9.966730,8.192182,0.060949")
(COMMAND "POINT" "10.037219,8.214191,0.057596")
(COMMAND "POINT" "10.106801,8.237743,0.054306")
(COMMAND "POINT" "10.175602,8.262643,0.051103")
(COMMAND "POINT" "10.243622,8.288890,0.047989")
(COMMAND "POINT" "10.310862,8.316484,0.044963")
(COMMAND "POINT" "10.377321,8.345426,0.042024")
(COMMAND "POINT" "10.443000,8.375714,0.039175")
(COMMAND "POINT" "10.507898,8.407349,0.036413")
(COMMAND "POINT" "10.572016,8.440332,0.033739")
(COMMAND "POINT" "10.635353,8.474662,0.031153")
(COMMAND "POINT" "10.697909,8.510339,0.028656")
(COMMAND "POINT" "10.759685,8.547363,0.026247")
(COMMAND "POINT" "10.820680,8.585734,0.023925")
(COMMAND "POINT" "10.880895,8.625453,0.021692")
(COMMAND "POINT" "10.940329,8.666518,0.019547")
(COMMAND "POINT" "10.998982,8.708931,0.017491")
(COMMAND "POINT" "11.056855,8.752691,0.015522")
(COMMAND "POINT" "11.113948,8.797798,0.013641")
(COMMAND "POINT" "11.170259,8.844252,0.011849")
(COMMAND "POINT" "11.225791,8.892053,0.010145")
(COMMAND "POINT" "11.280541,8.941201,0.008529")
(COMMAND "POINT" "11.334511,8.991697,0.007001")
(COMMAND "POINT" "11.387701,9.043539,0.005561")
(COMMAND "POINT" "11.440110,9.096729,0.004209")
(COMMAND "POINT" "11.491738,9.151266,0.002946")
(COMMAND "POINT" "11.542586,9.207150,0.001770")
(COMMAND "POINT" "11.592653,9.264382,0.000683")
(COMMAND "POINT" "11.641939,9.322960,-0.000316")
(COMMAND "POINT" "11.690445,9.382885,-0.001227")
(COMMAND "POINT" "11.738171,9.444158,-0.002050")
(COMMAND "POINT" "11.785116,9.506778,-0.002785")
(COMMAND "POINT" "11.831280,9.570745,-0.003432")
(COMMAND "POINT" "11.876664,9.636059,-0.003990")
(COMMAND "POINT" "11.921267,9.702720,-0.004461")
(COMMAND "POINT" "11.965089,9.770728,-0.004843")
(COMMAND "POINT" "12.008131,9.840084,-0.005137")
(COMMAND "POINT" "12.050393,9.910787,-0.005343")
(COMMAND "POINT" "12.091873,9.982836,-0.005461")
(COMMAND "POINT" "12.132574,10.056233,-0.005490")
(COMMAND "POINT" "12.172493,10.130977,-0.005432")
(COMMAND "POINT" "12.211632,10.207069,-0.005285")
(COMMAND "POINT" "12.249991,10.284507,-0.005051")
(COMMAND "POINT" "12.287569,10.363293,-0.004728")
(COMMAND "POINT" "12.324366,10.443425,-0.004317")
(COMMAND "POINT" "12.360383,10.524905,-0.003818")
(COMMAND "POINT" "12.395619,10.607732,-0.003230")
(COMMAND "POINT" "12.430074,10.691906,-0.002555")
(COMMAND "POINT" "12.463750,10.777427,-0.001791")
(COMMAND "POINT" "12.496644,10.864296,-0.000940")
(COMMAND "POINT" "12.528758,10.952511,0.000000")
(COMMAND "POINT" "4.429204,10.932093,0.095364")
(COMMAND "POINT" "4.579218,10.807850,0.099085")
(COMMAND "POINT" "4.727638,10.686633,0.102639")
(COMMAND "POINT" "4.874465,10.568444,0.106025")
(COMMAND "POINT" "5.019699,10.453281,0.109244")
(COMMAND "POINT" "5.163339,10.341145,0.112295")
(COMMAND "POINT" "5.305386,10.232035,0.115180")
(COMMAND "POINT" "5.445839,10.125952,0.117896")
(COMMAND "POINT" "5.584699,10.022896,0.120446")
(COMMAND "POINT" "5.721966,9.922867,0.122828")
(COMMAND "POINT" "5.857639,9.825864,0.125042")
(COMMAND "POINT" "5.991718,9.731888,0.127089")
(COMMAND "POINT" "6.124204,9.640939,0.128969")
(COMMAND "POINT" "6.255097,9.553017,0.130681")
(COMMAND "POINT" "6.384396,9.468121,0.132226")
(COMMAND "POINT" "6.512102,9.386252,0.133604")
(COMMAND "POINT" "6.638215,9.307410,0.134814")
(COMMAND "POINT" "6.762734,9.231594,0.135857")
(COMMAND "POINT" "6.885659,9.158806,0.136732")
(COMMAND "POINT" "7.006991,9.089044,0.137440")
(COMMAND "POINT" "7.126730,9.022308,0.137981")
(COMMAND "POINT" "7.244875,8.958600,0.138354")
(COMMAND "POINT" "7.361427,8.897918,0.138560")
(COMMAND "POINT" "7.476385,8.840262,0.138598")
(COMMAND "POINT" "7.589750,8.785634,0.138469")
(COMMAND "POINT" "7.701522,8.734032,0.138172")
(COMMAND "POINT" "7.811700,8.685457,0.137709")
(COMMAND "POINT" "7.920284,8.639909,0.137077")
(COMMAND "POINT" "8.027275,8.597387,0.136279")
(COMMAND "POINT" "8.132673,8.557892,0.135313")
(COMMAND "POINT" "8.236477,8.521424,0.134179")
(COMMAND "POINT" "8.338688,8.487983,0.132878")
(COMMAND "POINT" "8.439306,8.457568,0.131410")
(COMMAND "POINT" "8.538330,8.430180,0.129774")
(COMMAND "POINT" "8.635760,8.405819,0.127971")
(COMMAND "POINT" "8.731597,8.384484,0.126001")
(COMMAND "POINT" "8.825841,8.366177,0.123863")
(COMMAND "POINT" "8.918491,8.350896,0.121558")
(COMMAND "POINT" "9.009548,8.338641,0.119085")
(COMMAND "POINT" "9.099012,8.329414,0.116445")
(COMMAND "POINT" "9.186882,8.323213,0.113638")
(COMMAND "POINT" "9.273158,8.320038,0.110663")
(COMMAND "POINT" "9.357841,8.319891,0.107521")
(COMMAND "POINT" "9.440931,8.322770,0.104211")
(COMMAND "POINT" "9.522427,8.328676,0.100734")
(COMMAND "POINT" "9.602330,8.337609,0.097090")
(COMMAND "POINT" "9.680639,8.349568,0.093278")
(COMMAND "POINT" "9.757355,8.364555,0.089299")
(COMMAND "POINT" "9.832478,8.382567,0.085152")
(COMMAND "POINT" "9.906007,8.403607,0.080838")
(COMMAND "POINT" "9.978039,8.427461,0.076392")
(COMMAND "POINT" "10.049156,8.452857,0.072028")
(COMMAND "POINT" "10.119454,8.479584,0.067780")
(COMMAND "POINT" "10.188933,8.507640,0.063649")
(COMMAND "POINT" "10.257594,8.537026,0.059635")
(COMMAND "POINT" "10.325435,8.567741,0.055738")
(COMMAND "POINT" "10.392458,8.599787,0.051958")
(COMMAND "POINT" "10.458663,8.633163,0.048295")
(COMMAND "POINT" "10.524048,8.667869,0.044749")
(COMMAND "POINT" "10.588615,8.703904,0.041320")
(COMMAND "POINT" "10.652362,8.741270,0.038007")
(COMMAND "POINT" "10.715292,8.779965,0.034812")
(COMMAND "POINT" "10.777402,8.819990,0.031733")
(COMMAND "POINT" "10.838693,8.861345,0.028771")
(COMMAND "POINT" "10.899166,8.904030,0.025926")
(COMMAND "POINT" "10.958820,8.948045,0.023198")
(COMMAND "POINT" "11.017655,8.993390,0.020587")
(COMMAND "POINT" "11.075672,9.040065,0.018093")
(COMMAND "POINT" "11.132870,9.088070,0.015716")
(COMMAND "POINT" "11.189248,9.137405,0.013455")
(COMMAND "POINT" "11.244809,9.188069,0.011312")
(COMMAND "POINT" "11.299550,9.240064,0.009285")
(COMMAND "POINT" "11.353473,9.293388,0.007376")
(COMMAND "POINT" "11.406576,9.348042,0.005583")
(COMMAND "POINT" "11.458861,9.404026,0.003907")
(COMMAND "POINT" "11.510328,9.461341,0.002348")
(COMMAND "POINT" "11.560975,9.519985,0.000906")
(COMMAND "POINT" "11.610804,9.579959,-0.000420")
(COMMAND "POINT" "11.659814,9.641262,-0.001628")
(COMMAND "POINT" "11.708005,9.703896,-0.002719")
(COMMAND "POINT" "11.755377,9.767860,-0.003694")
(COMMAND "POINT" "11.801931,9.833153,-0.004552")
(COMMAND "POINT" "11.847666,9.899777,-0.005292")
(COMMAND "POINT" "11.892582,9.967730,-0.005916")
(COMMAND "POINT" "11.936679,10.037014,-0.006423")
(COMMAND "POINT" "11.979958,10.107627,-0.006813")
(COMMAND "POINT" "12.022418,10.179570,-0.007086")
(COMMAND "POINT" "12.064059,10.252843,-0.007243")
(COMMAND "POINT" "12.104881,10.327446,-0.007282")
(COMMAND "POINT" "12.144884,10.403379,-0.007204")
(COMMAND "POINT" "12.184069,10.480642,-0.007010")
(COMMAND "POINT" "12.222435,10.559234,-0.006699")
(COMMAND "POINT" "12.259982,10.639157,-0.006271")
(COMMAND "POINT" "12.296710,10.720410,-0.005725")
(COMMAND "POINT" "12.332620,10.802992,-0.005063")
(COMMAND "POINT" "12.367711,10.886904,-0.004285")
(COMMAND "POINT" "12.401983,10.972147,-0.003389")
(COMMAND "POINT" "12.435436,11.058719,-0.002376")
(COMMAND "POINT" "12.468070,11.146621,-0.001246")
(COMMAND "POINT" "12.499886,11.235853,0.000000")
(COMMAND "POINT" "4.530767,11.171674,0.120113")
(COMMAND "POINT" "4.672770,11.044785,0.124800")
(COMMAND "POINT" "4.813377,10.921010,0.129276")
(COMMAND "POINT" "4.952589,10.800348,0.133541")
(COMMAND "POINT" "5.090404,10.682800,0.137595")
(COMMAND "POINT" "5.226823,10.568367,0.141439")
(COMMAND "POINT" "5.361847,10.457046,0.145072")
(COMMAND "POINT" "5.495474,10.348840,0.148493")
(COMMAND "POINT" "5.627705,10.243747,0.151704")
(COMMAND "POINT" "5.758541,10.141769,0.154704")
(COMMAND "POINT" "5.887980,10.042904,0.157494")
(COMMAND "POINT" "6.016023,9.947153,0.160072")
(COMMAND "POINT" "6.142670,9.854515,0.162440")
(COMMAND "POINT" "6.267922,9.764992,0.164596")
(COMMAND "POINT" "6.391777,9.678582,0.166542")
(COMMAND "POINT" "6.514236,9.595286,0.168277")
(COMMAND "POINT" "6.635299,9.515104,0.169802")
(COMMAND "POINT" "6.754967,9.438036,0.171115")
(COMMAND "POINT" "6.873238,9.364081,0.172218")
(COMMAND "POINT" "6.990113,9.293241,0.173109")
(COMMAND "POINT" "7.105592,9.225514,0.173790")
(COMMAND "POINT" "7.219676,9.160901,0.174260")
(COMMAND "POINT" "7.332363,9.099402,0.174519")
(COMMAND "POINT" "7.443654,9.041016,0.174568")
(COMMAND "POINT" "7.553549,8.985745,0.174405")
(COMMAND "POINT" "7.662049,8.933587,0.174032")
(COMMAND "POINT" "7.769152,8.884543,0.173447")
(COMMAND "POINT" "7.874859,8.838613,0.172652")
(COMMAND "POINT" "7.979170,8.795796,0.171646")
(COMMAND "POINT" "8.082085,8.756094,0.170430")
(COMMAND "POINT" "8.183604,8.719505,0.169002")
(COMMAND "POINT" "8.283728,8.686030,0.167364")
(COMMAND "POINT" "8.382455,8.655669,0.165514")
(COMMAND "POINT" "8.479786,8.628421,0.163454")
(COMMAND "POINT" "8.575721,8.604288,0.161183")
(COMMAND "POINT" "8.670260,8.583268,0.158701")
(COMMAND "POINT" "8.763403,8.565362,0.156009")
(COMMAND "POINT" "8.855150,8.550570,0.153105")
(COMMAND "POINT" "8.945502,8.538892,0.149991")
(COMMAND "POINT" "9.034457,8.530327,0.146666")
(COMMAND "POINT" "9.122016,8.524877,0.143130")
(COMMAND "POINT" "9.208179,8.522540,0.139383")
(COMMAND "POINT" "9.292946,8.523317,0.135425")
(COMMAND "POINT" "9.376317,8.527207,0.131257")
(COMMAND "POINT" "9.458292,8.534212,0.126877")
(COMMAND "POINT" "9.538871,8.544330,0.122287")
(COMMAND "POINT" "9.618054,8.557562,0.117486")
(COMMAND "POINT" "9.695841,8.573908,0.112474")
(COMMAND "POINT" "9.772232,8.593368,0.107251")
(COMMAND "POINT" "9.847227,8.615942,0.101818")
(COMMAND "POINT" "9.920894,8.641404,0.096218")
(COMMAND "POINT" "9.993639,8.668407,0.090721")
(COMMAND "POINT" "10.065530,8.696726,0.085371")
(COMMAND "POINT" "10.136566,8.726359,0.080168")
(COMMAND "POINT" "10.206748,8.757308,0.075112")
(COMMAND "POINT" "10.276076,8.789573,0.070204")
(COMMAND "POINT" "10.344550,8.823153,0.065443")
(COMMAND "POINT" "10.412169,8.858049,0.060829")
(COMMAND "POINT" "10.478935,8.894260,0.056363")
(COMMAND "POINT" "10.544846,8.931786,0.052043")
(COMMAND "POINT" "10.609902,8.970628,0.047871")
(COMMAND "POINT" "10.674105,9.010785,0.043846")
(COMMAND "POINT" "10.737454,9.052258,0.039969")
(COMMAND "POINT" "10.799948,9.095046,0.036238")
(COMMAND "POINT" "10.861588,9.139150,0.032655")
(COMMAND "POINT" "10.922373,9.184569,0.029219")
(COMMAND "POINT" "10.982305,9.231304,0.025930")
(COMMAND "POINT" "11.041382,9.279354,0.022789")
(COMMAND "POINT" "11.099605,9.328719,0.019794")
(COMMAND "POINT" "11.156974,9.379400,0.016947")
(COMMAND "POINT" "11.213489,9.431397,0.014248")
(COMMAND "POINT" "11.269149,9.484708,0.011695")
(COMMAND "POINT" "11.323955,9.539336,0.009290")
(COMMAND "POINT" "11.377907,9.595278,0.007032")
(COMMAND "POINT" "11.431005,9.652536,0.004921")
(COMMAND "POINT" "11.483249,9.711110,0.002957")
(COMMAND "POINT" "11.534638,9.770999,0.001141")
(COMMAND "POINT" "11.585173,9.832204,-0.000528")
(COMMAND "POINT" "11.634854,9.894724,-0.002050")
(COMMAND "POINT" "11.683681,9.958559,-0.003425")
(COMMAND "POINT" "11.731653,10.023710,-0.004653")
(COMMAND "POINT" "11.778771,10.090176,-0.005733")
(COMMAND "POINT" "11.825035,10.157958,-0.006666")
(COMMAND "POINT" "11.870445,10.227055,-0.007452")
(COMMAND "POINT" "11.915001,10.297468,-0.008090")
(COMMAND "POINT" "11.958702,10.369196,-0.008581")
(COMMAND "POINT" "12.001549,10.442239,-0.008925")
(COMMAND "POINT" "12.043542,10.516598,-0.009122")
(COMMAND "POINT" "12.084681,10.592273,-0.009172")
(COMMAND "POINT" "12.124965,10.669263,-0.009074")
(COMMAND "POINT" "12.164396,10.747568,-0.008829")
(COMMAND "POINT" "12.202972,10.827189,-0.008437")
(COMMAND "POINT" "12.240693,10.908125,-0.007898")
(COMMAND "POINT" "12.277561,10.990377,-0.007211")
(COMMAND "POINT" "12.313574,11.073944,-0.006378")
(COMMAND "POINT" "12.348734,11.158827,-0.005396")
(COMMAND "POINT" "12.383039,11.245025,-0.004268")
(COMMAND "POINT" "12.416489,11.332538,-0.002993")
(COMMAND "POINT" "12.449086,11.421367,-0.001570")
(COMMAND "POINT" "12.480828,11.511511,0.000000")
(COMMAND "POINT" "4.620398,11.401690,0.146148")
(COMMAND "POINT" "4.754860,11.272804,0.151851")
(COMMAND "POINT" "4.888115,11.147101,0.157297")
(COMMAND "POINT" "5.020164,11.024580,0.162487")
(COMMAND "POINT" "5.151006,10.905242,0.167420")
(COMMAND "POINT" "5.280642,10.789087,0.172097")
(COMMAND "POINT" "5.409072,10.676115,0.176517")
(COMMAND "POINT" "5.536296,10.566325,0.180680")
(COMMAND "POINT" "5.662313,10.459718,0.184587")
(COMMAND "POINT" "5.787124,10.356294,0.188238")
(COMMAND "POINT" "5.910728,10.256053,0.191631")
(COMMAND "POINT" "6.033127,10.158994,0.194769")
(COMMAND "POINT" "6.154319,10.065118,0.197649")
(COMMAND "POINT" "6.274305,9.974425,0.200274")
(COMMAND "POINT" "6.393084,9.886915,0.202641")
(COMMAND "POINT" "6.510657,9.802587,0.204752")
(COMMAND "POINT" "6.627024,9.721442,0.206607")
(COMMAND "POINT" "6.742184,9.643480,0.208205")
(COMMAND "POINT" "6.856139,9.568701,0.209547")
(COMMAND "POINT" "6.968887,9.497104,0.210632")
(COMMAND "POINT" "7.080428,9.428690,0.211460")
(COMMAND "POINT" "7.190763,9.363459,0.212032")
(COMMAND "POINT" "7.299892,9.301411,0.212347")
(COMMAND "POINT" "7.407815,9.242545,0.212406")
(COMMAND "POINT" "7.514532,9.186862,0.212208")
(COMMAND "POINT" "7.620042,9.134362,0.211754")
(COMMAND "POINT" "7.724345,9.085045,0.211043")
(COMMAND "POINT" "7.827443,9.038910,0.210076")
(COMMAND "POINT" "7.929334,8.995959,0.208852")
(COMMAND "POINT" "8.030019,8.956190,0.207371")
(COMMAND "POINT" "8.129497,8.919603,0.205634")
(COMMAND "POINT" "8.227770,8.886200,0.203641")
(COMMAND "POINT" "8.324836,8.855979,0.201390")
(COMMAND "POINT" "8.420695,8.828941,0.198884")
(COMMAND "POINT" "8.515349,8.805086,0.196121")
(COMMAND "POINT" "8.608796,8.784413,0.193101")
(COMMAND "POINT" "8.701036,8.766923,0.189825")
(COMMAND "POINT" "8.792071,8.752616,0.186292")
(COMMAND "POINT" "8.881899,8.741492,0.182502")
(COMMAND "POINT" "8.970521,8.733550,0.178456")
(COMMAND "POINT" "9.057936,8.728792,0.174154")
(COMMAND "POINT" "9.144146,8.727216,0.169595")
(COMMAND "POINT" "9.229148,8.728822,0.164779")
(COMMAND "POINT" "9.312945,8.733612,0.159707")
(COMMAND "POINT" "9.395535,8.741584,0.154378")
(COMMAND "POINT" "9.476919,8.752739,0.148793")
(COMMAND "POINT" "9.557097,8.767077,0.142952")
(COMMAND "POINT" "9.636068,8.784597,0.136853")
(COMMAND "POINT" "9.713834,8.805301,0.130498")
(COMMAND "POINT" "9.790392,8.829187,0.123887")
(COMMAND "POINT" "9.865785,8.856020,0.117074")
(COMMAND "POINT" "9.940250,8.884393,0.110385")
(COMMAND "POINT" "10.013829,8.914069,0.103875")
(COMMAND "POINT" "10.086521,8.945049,0.097545")
(COMMAND "POINT" "10.158325,8.977333,0.091393")
(COMMAND "POINT" "10.229243,9.010920,0.085421")
(COMMAND "POINT" "10.299274,9.045812,0.079628")
(COMMAND "POINT" "10.368418,9.082007,0.074014")
(COMMAND "POINT" "10.436676,9.119506,0.068579")
(COMMAND "POINT" "10.504046,9.158308,0.063324")
(COMMAND "POINT" "10.570529,9.198414,0.058247")
(COMMAND "POINT" "10.636125,9.239824,0.053350")
(COMMAND "POINT" "10.700835,9.282538,0.048632")
(COMMAND "POINT" "10.764658,9.326556,0.044093")
(COMMAND "POINT" "10.827593,9.371877,0.039733")
(COMMAND "POINT" "10.889642,9.418502,0.035552")
(COMMAND "POINT" "10.950804,9.466431,0.031551")
(COMMAND "POINT" "11.011079,9.515663,0.027728")
(COMMAND "POINT" "11.070467,9.566200,0.024085")
(COMMAND "POINT" "11.128968,9.618040,0.020621")
(COMMAND "POINT" "11.186582,9.671184,0.017336")
(COMMAND "POINT" "11.243309,9.725631,0.014230")
(COMMAND "POINT" "11.299149,9.781382,0.011303")
(COMMAND "POINT" "11.354103,9.838438,0.008556")
(COMMAND "POINT" "11.408169,9.896796,0.005987")
(COMMAND "POINT" "11.461349,9.956459,0.003598")
(COMMAND "POINT" "11.513642,10.017425,0.001388")
(COMMAND "POINT" "11.565047,10.079695,-0.000643")
(COMMAND "POINT" "11.615566,10.143269,-0.002495")
(COMMAND "POINT" "11.665198,10.208147,-0.004167")
(COMMAND "POINT" "11.713943,10.274328,-0.005661")
(COMMAND "POINT" "11.761801,10.341813,-0.006975")
(COMMAND "POINT" "11.808772,10.410602,-0.008111")
(COMMAND "POINT" "11.854857,10.480695,-0.009067")
(COMMAND "POINT" "11.900054,10.552091,-0.009844")
(COMMAND "POINT" "11.944364,10.624791,-0.010441")
(COMMAND "POINT" "11.987788,10.698795,-0.010860")
(COMMAND "POINT" "12.030324,10.774102,-0.011100")
(COMMAND "POINT" "12.071974,10.850714,-0.011160")
(COMMAND "POINT" "12.112737,10.928629,-0.011041")
(COMMAND "POINT" "12.152613,11.007848,-0.010743")
(COMMAND "POINT" "12.191602,11.088370,-0.010266")
(COMMAND "POINT" "12.229704,11.170197,-0.009610")
(COMMAND "POINT" "12.266919,11.253327,-0.008774")
(COMMAND "POINT" "12.303247,11.337761,-0.007760")
(COMMAND "POINT" "12.338688,11.423498,-0.006566")
(COMMAND "POINT" "12.373242,11.510540,-0.005193")
(COMMAND "POINT" "12.406910,11.598885,-0.003641")
(COMMAND "POINT" "12.439690,11.688534,-0.001910")
(COMMAND "POINT" "12.471584,11.779486,0.000000")
(COMMAND "POINT" "4.698100,11.622140,0.173469")
(COMMAND "POINT" "4.825488,11.491906,0.180238")
(COMMAND "POINT" "4.951851,11.364906,0.186702")
(COMMAND "POINT" "5.077191,11.241139,0.192862")
(COMMAND "POINT" "5.201506,11.120605,0.198718")
(COMMAND "POINT" "5.324796,11.003306,0.204268")
(COMMAND "POINT" "5.447063,10.889240,0.209515")
(COMMAND "POINT" "5.568305,10.778407,0.214457")
(COMMAND "POINT" "5.688522,10.670808,0.219094")
(COMMAND "POINT" "5.807716,10.566442,0.223427")
(COMMAND "POINT" "5.925885,10.465311,0.227455")
(COMMAND "POINT" "6.043029,10.367412,0.231179")
(COMMAND "POINT" "6.159150,10.272747,0.234598")
(COMMAND "POINT" "6.274246,10.181316,0.237713")
(COMMAND "POINT" "6.388318,10.093118,0.240523")
(COMMAND "POINT" "6.501365,10.008154,0.243029")
(COMMAND "POINT" "6.613388,9.926424,0.245230")
(COMMAND "POINT" "6.724387,9.847927,0.247127")
(COMMAND "POINT" "6.834361,9.772663,0.248719")
(COMMAND "POINT" "6.943311,9.700633,0.250007")
(COMMAND "POINT" "7.051237,9.631837,0.250990")
(COMMAND "POINT" "7.158138,9.566274,0.251669")
(COMMAND "POINT" "7.264016,9.503945,0.252043")
(COMMAND "POINT" "7.368868,9.444849,0.252113")
(COMMAND "POINT" "7.472697,9.388987,0.251878")
(COMMAND "POINT" "7.575501,9.336359,0.251339")
(COMMAND "POINT" "7.677281,9.286964,0.250495")
(COMMAND "POINT" "7.778036,9.240802,0.249347")
(COMMAND "POINT" "7.877767,9.197874,0.247894")
(COMMAND "POINT" "7.976474,9.158180,0.246137")
(COMMAND "POINT" "8.074157,9.121719,0.244075")
(COMMAND "POINT" "8.170815,9.088492,0.241709")
(COMMAND "POINT" "8.266448,9.058498,0.239038")
(COMMAND "POINT" "8.361058,9.031738,0.236063")
(COMMAND "POINT" "8.454643,9.008212,0.232783")
(COMMAND "POINT" "8.547204,8.987919,0.229199")
(COMMAND "POINT" "8.638740,8.970860,0.225310")
(COMMAND "POINT" "8.729253,8.957034,0.221117")
(COMMAND "POINT" "8.818741,8.946441,0.216619")
(COMMAND "POINT" "8.907204,8.939083,0.211817")
(COMMAND "POINT" "8.994643,8.934957,0.206710")
(COMMAND "POINT" "9.081058,8.934066,0.201299")
(COMMAND "POINT" "9.166449,8.936408,0.195583")
(COMMAND "POINT" "9.250815,8.941983,0.189563")
(COMMAND "POINT" "9.334157,8.950792,0.183238")
(COMMAND "POINT" "9.416474,8.962835,0.176609")
(COMMAND "POINT" "9.497768,8.978111,0.169675")
(COMMAND "POINT" "9.578036,8.996621,0.162437")
(COMMAND "POINT" "9.657281,9.018364,0.154894")
(COMMAND "POINT" "9.735501,9.043341,0.147047")
(COMMAND "POINT" "9.812711,9.071309,0.138959")
(COMMAND "POINT" "9.888990,9.100814,0.131020")
(COMMAND "POINT" "9.964352,9.131614,0.123294")
(COMMAND "POINT" "10.038797,9.163709,0.115780")
(COMMAND "POINT" "10.112326,9.197099,0.108478")
(COMMAND "POINT" "10.184937,9.231784,0.101390")
(COMMAND "POINT" "10.256632,9.267763,0.094514")
(COMMAND "POINT" "10.327410,9.305037,0.087850")
(COMMAND "POINT" "10.397271,9.343606,0.081400")
(COMMAND "POINT" "10.466215,9.383470,0.075162")
(COMMAND "POINT" "10.534242,9.424629,0.069136")
(COMMAND "POINT" "10.601353,9.467082,0.063323")
(COMMAND "POINT" "10.667546,9.510830,0.057723")
(COMMAND "POINT" "10.732823,9.555873,0.052336")
(COMMAND "POINT" "10.797183,9.602211,0.047161")
(COMMAND "POINT" "10.860626,9.649844,0.042198")
(COMMAND "POINT" "10.923152,9.698772,0.037449")
(COMMAND "POINT" "10.984761,9.748994,0.032912")
(COMMAND "POINT" "11.045454,9.800511,0.028587")
(COMMAND "POINT" "11.105229,9.853323,0.024476")
(COMMAND "POINT" "11.164088,9.907430,0.020577")
(COMMAND "POINT" "11.222030,9.962832,0.016890")
(COMMAND "POINT" "11.279055,10.019528,0.013416")
(COMMAND "POINT" "11.335163,10.077520,0.010155")
(COMMAND "POINT" "11.390354,10.136806,0.007107")
(COMMAND "POINT" "11.444628,10.197387,0.004271")
(COMMAND "POINT" "11.497986,10.259263,0.001647")
(COMMAND "POINT" "11.550426,10.322433,-0.000763")
(COMMAND "POINT" "11.601950,10.386899,-0.002961")
(COMMAND "POINT" "11.652557,10.452659,-0.004947")
(COMMAND "POINT" "11.702247,10.519714,-0.006719")
(COMMAND "POINT" "11.751020,10.588064,-0.008279")
(COMMAND "POINT" "11.798876,10.657709,-0.009627")
(COMMAND "POINT" "11.845816,10.728648,-0.010762")
(COMMAND "POINT" "11.891838,10.800883,-0.011684")
(COMMAND "POINT" "11.936944,10.874412,-0.012393")
(COMMAND "POINT" "11.981133,10.949236,-0.012890")
(COMMAND "POINT" "12.024405,11.025355,-0.013174")
(COMMAND "POINT" "12.066760,11.102769,-0.013246")
(COMMAND "POINT" "12.108198,11.181477,-0.013105")
(COMMAND "POINT" "12.148720,11.261480,-0.012751")
(COMMAND "POINT" "12.188324,11.342779,-0.012185")
(COMMAND "POINT" "12.227012,11.425372,-0.011406")
(COMMAND "POINT" "12.264783,11.509259,-0.010415")
(COMMAND "POINT" "12.301637,11.594442,-0.009211")
(COMMAND "POINT" "12.337574,11.680919,-0.007794")
(COMMAND "POINT" "12.372594,11.768692,-0.006164")
(COMMAND "POINT" "12.406698,11.857759,-0.004322")
(COMMAND "POINT" "12.439884,11.948121,-0.002267")
(COMMAND "POINT" "12.472154,12.039777,0.000000")
(COMMAND "POINT" "4.763870,11.833024,0.202076")
(COMMAND "POINT" "4.884653,11.702091,0.209961")
(COMMAND "POINT" "5.004586,11.574425,0.217492")
(COMMAND "POINT" "5.123669,11.450025,0.224667")
(COMMAND "POINT" "5.241902,11.328891,0.231488")
(COMMAND "POINT" "5.359285,11.211023,0.237954")
(COMMAND "POINT" "5.475818,11.096422,0.244066")
(COMMAND "POINT" "5.591501,10.985086,0.249823")
(COMMAND "POINT" "5.706333,10.877017,0.255225")
(COMMAND "POINT" "5.820316,10.772214,0.260272")
(COMMAND "POINT" "5.933448,10.670678,0.264965")
(COMMAND "POINT" "6.045731,10.572408,0.269303")
(COMMAND "POINT" "6.157163,10.477403,0.273286")
(COMMAND "POINT" "6.267745,10.385665,0.276914")
(COMMAND "POINT" "6.377477,10.297194,0.280188")
(COMMAND "POINT" "6.486360,10.211988,0.283107")
(COMMAND "POINT" "6.594392,10.130049,0.285671")
(COMMAND "POINT" "6.701574,10.051376,0.287881")
(COMMAND "POINT" "6.807905,9.975969,0.289736")
(COMMAND "POINT" "6.913387,9.903829,0.291236")
(COMMAND "POINT" "7.018019,9.834954,0.292381")
(COMMAND "POINT" "7.121800,9.769346,0.293172")
(COMMAND "POINT" "7.224732,9.707004,0.293608")
(COMMAND "POINT" "7.326813,9.647929,0.293689")
(COMMAND "POINT" "7.428045,9.592119,0.293416")
(COMMAND "POINT" "7.528426,9.539576,0.292788")
(COMMAND "POINT" "7.627957,9.490299,0.291805")
(COMMAND "POINT" "7.726639,9.444288,0.290467")
(COMMAND "POINT" "7.824470,9.401544,0.288775")
(COMMAND "POINT" "7.921451,9.362065,0.286728")
(COMMAND "POINT" "8.017582,9.325853,0.284326")
(COMMAND "POINT" "8.112862,9.292907,0.281570")
(COMMAND "POINT" "8.207293,9.263228,0.278458")
(COMMAND "POINT" "8.300874,9.236814,0.274992")
(COMMAND "POINT" "8.393604,9.213667,0.271172")
(COMMAND "POINT" "8.485485,9.193786,0.266996")
(COMMAND "POINT" "8.576515,9.177171,0.262466")
(COMMAND "POINT" "8.666696,9.163823,0.257582")
(COMMAND "POINT" "8.756026,9.153740,0.252342")
(COMMAND "POINT" "8.844506,9.146924,0.246748")
(COMMAND "POINT" "8.932137,9.143374,0.240799")
(COMMAND "POINT" "9.018917,9.143091,0.234495")
(COMMAND "POINT" "9.104847,9.146073,0.227837")
(COMMAND "POINT" "9.189926,9.152322,0.220824")
(COMMAND "POINT" "9.274156,9.161837,0.213456")
(COMMAND "POINT" "9.357536,9.174618,0.205733")
(COMMAND "POINT" "9.440066,9.190666,0.197656")
(COMMAND "POINT" "9.521745,9.209980,0.189224")
(COMMAND "POINT" "9.602575,9.232559,0.180437")
(COMMAND "POINT" "9.682554,9.258406,0.171296")
(COMMAND "POINT" "9.761672,9.287271,0.161875")
(COMMAND "POINT" "9.839857,9.317672,0.152627")
(COMMAND "POINT" "9.917098,9.349361,0.143626")
(COMMAND "POINT" "9.993396,9.382340,0.134873")
(COMMAND "POINT" "10.068749,9.416607,0.126368")
(COMMAND "POINT" "10.143158,9.452162,0.118110")
(COMMAND "POINT" "10.216623,9.489007,0.110100")
(COMMAND "POINT" "10.289144,9.527140,0.102338")
(COMMAND "POINT" "10.360721,9.566561,0.094823")
(COMMAND "POINT" "10.431353,9.607272,0.087557")
(COMMAND "POINT" "10.501042,9.649271,0.080537")
(COMMAND "POINT" "10.569787,9.692558,0.073766")
(COMMAND "POINT" "10.637588,9.737135,0.067242")
(COMMAND "POINT" "10.704444,9.782999,0.060966")
(COMMAND "POINT" "10.770357,9.830153,0.054938")
(COMMAND "POINT" "10.835325,9.878595,0.049157")
(COMMAND "POINT" "10.899350,9.928326,0.043624")
(COMMAND "POINT" "10.962430,9.979346,0.038339")
(COMMAND "POINT" "11.024566,10.031654,0.033302")
(COMMAND "POINT" "11.085758,10.085251,0.028512")
(COMMAND "POINT" "11.146007,10.140137,0.023970")
(COMMAND "POINT" "11.205311,10.196311,0.019676")
(COMMAND "POINT" "11.263671,10.253774,0.015629")
(COMMAND "POINT" "11.321087,10.312525,0.011830")
(COMMAND "POINT" "11.377559,10.372565,0.008279")
(COMMAND "POINT" "11.433086,10.433894,0.004975")
(COMMAND "POINT" "11.487670,10.496512,0.001919")
(COMMAND "POINT" "11.541310,10.560418,-0.000889")
(COMMAND "POINT" "11.594006,10.625613,-0.003449")
(COMMAND "POINT" "11.645757,10.692096,-0.005762")
(COMMAND "POINT" "11.696565,10.759869,-0.007827")
(COMMAND "POINT" "11.746428,10.828929,-0.009645")
(COMMAND "POINT" "11.795348,10.899279,-0.011214")
(COMMAND "POINT" "11.843323,10.970917,-0.012536")
(COMMAND "POINT" "11.890355,11.043844,-0.013611")
(COMMAND "POINT" "11.936442,11.118059,-0.014437")
(COMMAND "POINT" "11.981585,11.193563,-0.015016")
(COMMAND "POINT" "12.025784,11.270356,-0.015347")
(COMMAND "POINT" "12.069039,11.348438,-0.015431")
(COMMAND "POINT" "12.111350,11.427808,-0.015266")
(COMMAND "POINT" "12.152717,11.508467,-0.014854")
(COMMAND "POINT" "12.193140,11.590414,-0.014195")
(COMMAND "POINT" "12.232619,11.673650,-0.013287")
(COMMAND "POINT" "12.271154,11.758175,-0.012132")
(COMMAND "POINT" "12.308745,11.843988,-0.010729")
(COMMAND "POINT" "12.345391,11.931090,-0.009079")
(COMMAND "POINT" "12.381094,12.019481,-0.007181")
(COMMAND "POINT" "12.415852,12.109160,-0.005035")
(COMMAND "POINT" "12.449667,12.200128,-0.002641")
(COMMAND "POINT" "12.482537,12.292385,0.000000")
(COMMAND "POINT" "4.817710,12.034341,0.231969")
(COMMAND "POINT" "4.932357,11.903359,0.241020")
(COMMAND "POINT" "5.046320,11.775658,0.249665")
(COMMAND "POINT" "5.159600,11.651238,0.257902")
(COMMAND "POINT" "5.272196,11.530098,0.265732")
(COMMAND "POINT" "5.384109,11.412239,0.273155")
(COMMAND "POINT" "5.495338,11.297660,0.280170")
(COMMAND "POINT" "5.605884,11.186363,0.286778")
(COMMAND "POINT" "5.715746,11.078346,0.292980")
(COMMAND "POINT" "5.824925,10.973610,0.298774")
(COMMAND "POINT" "5.933420,10.872154,0.304160")
(COMMAND "POINT" "6.041231,10.773980,0.309140")
(COMMAND "POINT" "6.148359,10.679086,0.313712")
(COMMAND "POINT" "6.254803,10.587473,0.317878")
(COMMAND "POINT" "6.360564,10.499141,0.321636")
(COMMAND "POINT" "6.465641,10.414089,0.324986")
(COMMAND "POINT" "6.570035,10.332318,0.327930")
(COMMAND "POINT" "6.673745,10.253828,0.330467")
(COMMAND "POINT" "6.776771,10.178619,0.332596")
(COMMAND "POINT" "6.879114,10.106690,0.334318")
(COMMAND "POINT" "6.980774,10.038042,0.335633")
(COMMAND "POINT" "7.081750,9.972675,0.336540")
(COMMAND "POINT" "7.182042,9.910589,0.337041")
(COMMAND "POINT" "7.281651,9.851783,0.337134")
(COMMAND "POINT" "7.380576,9.796258,0.336820")
(COMMAND "POINT" "7.478818,9.744014,0.336099")
(COMMAND "POINT" "7.576376,9.695051,0.334971")
(COMMAND "POINT" "7.673250,9.649368,0.333435")
(COMMAND "POINT" "7.769441,9.606966,0.331493")
(COMMAND "POINT" "7.864949,9.567845,0.329143")
(COMMAND "POINT" "7.959773,9.532005,0.326386")
(COMMAND "POINT" "8.053913,9.499445,0.323222")
(COMMAND "POINT" "8.147370,9.470166,0.319650")
(COMMAND "POINT" "8.240143,9.444168,0.315672")
(COMMAND "POINT" "8.332233,9.421451,0.311286")
(COMMAND "POINT" "8.423639,9.402014,0.306493")
(COMMAND "POINT" "8.514361,9.385858,0.301293")
(COMMAND "POINT" "8.604400,9.372983,0.295685")
(COMMAND "POINT" "8.693756,9.363389,0.289671")
(COMMAND "POINT" "8.782428,9.357075,0.283249")
(COMMAND "POINT" "8.870416,9.354042,0.276420")
(COMMAND "POINT" "8.957721,9.354290,0.269184")
(COMMAND "POINT" "9.044342,9.357819,0.261540")
(COMMAND "POINT" "9.130280,9.364628,0.253490")
(COMMAND "POINT" "9.215534,9.374718,0.245032")
(COMMAND "POINT" "9.300105,9.388089,0.236167")
(COMMAND "POINT" "9.383992,9.404741,0.226895")
(COMMAND "POINT" "9.467195,9.424673,0.217216")
(COMMAND "POINT" "9.549715,9.447886,0.207129")
(COMMAND "POINT" "9.631551,9.474380,0.196635")
(COMMAND "POINT" "9.712669,9.503905,0.185821")
(COMMAND "POINT" "9.792853,9.534965,0.175204")
(COMMAND "POINT" "9.872069,9.567310,0.164872")
(COMMAND "POINT" "9.950316,9.600940,0.154824")
(COMMAND "POINT" "10.027595,9.635856,0.145061")
(COMMAND "POINT" "10.103905,9.672057,0.135582")
(COMMAND "POINT" "10.179247,9.709543,0.126387")
(COMMAND "POINT" "10.253620,9.748315,0.117477")
(COMMAND "POINT" "10.327025,9.788371,0.108850")
(COMMAND "POINT" "10.399461,9.829713,0.100509")
(COMMAND "POINT" "10.470929,9.872341,0.092451")
(COMMAND "POINT" "10.541428,9.916253,0.084678")
(COMMAND "POINT" "10.610959,9.961451,0.077189")
(COMMAND "POINT" "10.679521,10.007934,0.069985")
(COMMAND "POINT" "10.747115,10.055702,0.063065")
(COMMAND "POINT" "10.813740,10.104756,0.056429")
(COMMAND "POINT" "10.879396,10.155094,0.050078")
(COMMAND "POINT" "10.944085,10.206719,0.044011")
(COMMAND "POINT" "11.007804,10.259628,0.038228")
(COMMAND "POINT" "11.070556,10.313823,0.032730")
(COMMAND "POINT" "11.132338,10.369302,0.027516")
(COMMAND "POINT" "11.193152,10.426068,0.022586")
(COMMAND "POINT" "11.252998,10.484118,0.017941")
(COMMAND "POINT" "11.311875,10.543454,0.013580")
(COMMAND "POINT" "11.369784,10.604075,0.009503")
(COMMAND "POINT" "11.426724,10.665981,0.005711")
(COMMAND "POINT" "11.482695,10.729172,0.002203")
(COMMAND "POINT" "11.537699,10.793649,-0.001021")
(COMMAND "POINT" "11.591733,10.859411,-0.003960")
(COMMAND "POINT" "11.644799,10.926458,-0.006615")
(COMMAND "POINT" "11.696897,10.994791,-0.008985")
(COMMAND "POINT" "11.748026,11.064409,-0.011071")
(COMMAND "POINT" "11.798187,11.135312,-0.012873")
(COMMAND "POINT" "11.847379,11.207500,-0.014391")
(COMMAND "POINT" "11.895602,11.280974,-0.015624")
(COMMAND "POINT" "11.942857,11.355733,-0.016573")
(COMMAND "POINT" "11.989144,11.431777,-0.017237")
(COMMAND "POINT" "12.034462,11.509106,-0.017617")
(COMMAND "POINT" "12.078811,11.587721,-0.017713")
(COMMAND "POINT" "12.122192,11.667621,-0.017525")
(COMMAND "POINT" "12.164605,11.748806,-0.017052")
(COMMAND "POINT" "12.206049,11.831276,-0.016294")
(COMMAND "POINT" "12.246524,11.915032,-0.015253")
(COMMAND "POINT" "12.286031,12.000073,-0.013927")
(COMMAND "POINT" "12.324570,12.086399,-0.012317")
(COMMAND "POINT" "12.362140,12.174011,-0.010422")
(COMMAND "POINT" "12.398741,12.262907,-0.008243")
(COMMAND "POINT" "12.434374,12.353090,-0.005780")
(COMMAND "POINT" "12.469039,12.444557,-0.003032")
(COMMAND "POINT" "12.502735,12.537309,0.000000")
(COMMAND "POINT" "4.859619,12.226093,0.263147")
(COMMAND "POINT" "4.968598,12.095711,0.273416")
(COMMAND "POINT" "5.077053,11.968606,0.283222")
(COMMAND "POINT" "5.184983,11.844778,0.292566")
(COMMAND "POINT" "5.292388,11.724227,0.301448")
(COMMAND "POINT" "5.399268,11.606953,0.309869")
(COMMAND "POINT" "5.505624,11.492956,0.317827")
(COMMAND "POINT" "5.611454,11.382236,0.325324")
(COMMAND "POINT" "5.716760,11.274794,0.332359")
(COMMAND "POINT" "5.821542,11.170629,0.338931")
(COMMAND "POINT" "5.925798,11.069740,0.345042")
(COMMAND "POINT" "6.029530,10.972129,0.350691")
(COMMAND "POINT" "6.132737,10.877795,0.355878")
(COMMAND "POINT" "6.235419,10.786739,0.360603")
(COMMAND "POINT" "6.337577,10.698959,0.364866")
(COMMAND "POINT" "6.439209,10.614456,0.368667")
(COMMAND "POINT" "6.540317,10.533231,0.372007")
(COMMAND "POINT" "6.640901,10.455283,0.374884")
(COMMAND "POINT" "6.740959,10.380612,0.377299")
(COMMAND "POINT" "6.840493,10.309218,0.379253")
(COMMAND "POINT" "6.939502,10.241101,0.380745")
(COMMAND "POINT" "7.037986,10.176261,0.381774")
(COMMAND "POINT" "7.135945,10.114698,0.382342")
(COMMAND "POINT" "7.233380,10.056413,0.382448")
(COMMAND "POINT" "7.330290,10.001405,0.382092")
(COMMAND "POINT" "7.426675,9.949673,0.381274")
(COMMAND "POINT" "7.522536,9.901219,0.379994")
(COMMAND "POINT" "7.617871,9.856042,0.378252")
(COMMAND "POINT" "7.712682,9.814143,0.376048")
(COMMAND "POINT" "7.806968,9.775520,0.373382")
(COMMAND "POINT" "7.900730,9.740174,0.370255")
(COMMAND "POINT" "7.993966,9.708106,0.366665")
(COMMAND "POINT" "8.086678,9.679315,0.362614")
(COMMAND "POINT" "8.178865,9.653801,0.358100")
(COMMAND "POINT" "8.270528,9.631564,0.353125")
(COMMAND "POINT" "8.361665,9.612604,0.347688")
(COMMAND "POINT" "8.452278,9.596921,0.341789")
(COMMAND "POINT" "8.542366,9.584515,0.335428")
(COMMAND "POINT" "8.631930,9.575387,0.328605")
(COMMAND "POINT" "8.720968,9.569535,0.321320")
(COMMAND "POINT" "8.809482,9.566961,0.313573")
(COMMAND "POINT" "8.897471,9.567664,0.305364")
(COMMAND "POINT" "8.984935,9.571644,0.296694")
(COMMAND "POINT" "9.071875,9.578901,0.287561")
(COMMAND "POINT" "9.158290,9.589436,0.277966")
(COMMAND "POINT" "9.244180,9.603247,0.267910")
(COMMAND "POINT" "9.329545,9.620336,0.257392")
(COMMAND "POINT" "9.414386,9.640701,0.246411")
(COMMAND "POINT" "9.498701,9.664344,0.234969")
(COMMAND "POINT" "9.582492,9.691264,0.223065")
(COMMAND "POINT" "9.665701,9.721212,0.210797")
(COMMAND "POINT" "9.747977,9.752694,0.198753")
(COMMAND "POINT" "9.829262,9.785460,0.187033")
(COMMAND "POINT" "9.909558,9.819511,0.175634")
(COMMAND "POINT" "9.988864,9.854847,0.164558")
(COMMAND "POINT" "10.067179,9.891467,0.153805")
(COMMAND "POINT" "10.144504,9.929372,0.143374")
(COMMAND "POINT" "10.220839,9.968562,0.133266")
(COMMAND "POINT" "10.296183,10.009036,0.123481")
(COMMAND "POINT" "10.370538,10.050795,0.114018")
(COMMAND "POINT" "10.443902,10.093838,0.104877")
(COMMAND "POINT" "10.516276,10.138166,0.096060")
(COMMAND "POINT" "10.587660,10.183779,0.087564")
(COMMAND "POINT" "10.658053,10.230676,0.079391")
(COMMAND "POINT" "10.727457,10.278858,0.071541")
(COMMAND "POINT" "10.795870,10.328325,0.064014")
(COMMAND "POINT" "10.863293,10.379076,0.056809")
(COMMAND "POINT" "10.929726,10.431112,0.049926")
(COMMAND "POINT" "10.995168,10.484433,0.043366")
(COMMAND "POINT" "11.059620,10.539038,0.037129")
(COMMAND "POINT" "11.123083,10.594928,0.031214")
(COMMAND "POINT" "11.185555,10.652102,0.025622")
(COMMAND "POINT" "11.247036,10.710562,0.020352")
(COMMAND "POINT" "11.307528,10.770305,0.015405")
(COMMAND "POINT" "11.367029,10.831334,0.010781")
(COMMAND "POINT" "11.425540,10.893647,0.006479")
(COMMAND "POINT" "11.483061,10.957244,0.002499")
(COMMAND "POINT" "11.539592,11.022127,-0.001158")
(COMMAND "POINT" "11.595133,11.088294,-0.004492")
(COMMAND "POINT" "11.649683,11.155745,-0.007504")
(COMMAND "POINT" "11.703243,11.224481,-0.010193")
(COMMAND "POINT" "11.755813,11.294502,-0.012559")
(COMMAND "POINT" "11.807393,11.365808,-0.014604")
(COMMAND "POINT" "11.857982,11.438398,-0.016325")
(COMMAND "POINT" "11.907581,11.512272,-0.017724")
(COMMAND "POINT" "11.956190,11.587432,-0.018800")
(COMMAND "POINT" "12.003809,11.663876,-0.019554")
(COMMAND "POINT" "12.050438,11.741605,-0.019985")
(COMMAND "POINT" "12.096076,11.820618,-0.020094")
(COMMAND "POINT" "12.140725,11.900916,-0.019880")
(COMMAND "POINT" "12.184383,11.982498,-0.019344")
(COMMAND "POINT" "12.227051,12.065366,-0.018485")
(COMMAND "POINT" "12.268728,12.149517,-0.017303")
(COMMAND "POINT" "12.309416,12.234954,-0.015799")
(COMMAND "POINT" "12.349113,12.321675,-0.013972")
(COMMAND "POINT" "12.387820,12.409681,-0.011823")
(COMMAND "POINT" "12.425537,12.498971,-0.009351")
(COMMAND "POINT" "12.462264,12.589546,-0.006557")
(COMMAND "POINT" "12.498000,12.681406,-0.003440")
(COMMAND "POINT" "12.532746,12.774550,0.000000")
(COMMAND "POINT" "4.889597,12.408279,0.295612")
(COMMAND "POINT" "4.993378,12.279146,0.307147")
(COMMAND "POINT" "5.096784,12.153267,0.318163")
(COMMAND "POINT" "5.199817,12.030645,0.328660")
(COMMAND "POINT" "5.302476,11.911277,0.338638")
(COMMAND "POINT" "5.404762,11.795165,0.348097")
(COMMAND "POINT" "5.506674,11.682309,0.357038")
(COMMAND "POINT" "5.608212,11.572707,0.365459")
(COMMAND "POINT" "5.709376,11.466361,0.373362")
(COMMAND "POINT" "5.810167,11.363271,0.380745")
(COMMAND "POINT" "5.910584,11.263436,0.387610")
(COMMAND "POINT" "6.010628,11.166856,0.393956")
(COMMAND "POINT" "6.110298,11.073531,0.399783")
(COMMAND "POINT" "6.209594,10.983462,0.405091")
(COMMAND "POINT" "6.308516,10.896649,0.409880")
(COMMAND "POINT" "6.407065,10.813091,0.414150")
(COMMAND "POINT" "6.505240,10.732788,0.417901")
(COMMAND "POINT" "6.603041,10.655740,0.421133")
(COMMAND "POINT" "6.700469,10.581948,0.423847")
(COMMAND "POINT" "6.797523,10.511411,0.426041")
(COMMAND "POINT" "6.894203,10.444130,0.427717")
(COMMAND "POINT" "6.990510,10.380104,0.428874")
(COMMAND "POINT" "7.086442,10.319333,0.429511")
(COMMAND "POINT" "7.182002,10.261818,0.429630")
(COMMAND "POINT" "7.277187,10.207558,0.429230")
(COMMAND "POINT" "7.371999,10.156554,0.428311")
(COMMAND "POINT" "7.466437,10.108804,0.426874")
(COMMAND "POINT" "7.560502,10.064311,0.424917")
(COMMAND "POINT" "7.654192,10.023072,0.422441")
(COMMAND "POINT" "7.747510,9.985089,0.419447")
(COMMAND "POINT" "7.840453,9.950362,0.415933")
(COMMAND "POINT" "7.933023,9.918889,0.411901")
(COMMAND "POINT" "8.025219,9.890673,0.407349")
(COMMAND "POINT" "8.117041,9.865711,0.402279")
(COMMAND "POINT" "8.208490,9.844005,0.396690")
(COMMAND "POINT" "8.299565,9.825554,0.390582")
(COMMAND "POINT" "8.390266,9.810359,0.383955")
(COMMAND "POINT" "8.480594,9.798419,0.376809")
(COMMAND "POINT" "8.570548,9.789734,0.369145")
(COMMAND "POINT" "8.660128,9.784305,0.360961")
(COMMAND "POINT" "8.749334,9.782131,0.352258")
(COMMAND "POINT" "8.838167,9.783213,0.343037")
(COMMAND "POINT" "8.926626,9.787550,0.333297")
(COMMAND "POINT" "9.014712,9.795142,0.323037")
(COMMAND "POINT" "9.102424,9.805989,0.312259")
(COMMAND "POINT" "9.189762,9.820092,0.300962")
(COMMAND "POINT" "9.276726,9.837451,0.289146")
(COMMAND "POINT" "9.363317,9.858065,0.276811")
(COMMAND "POINT" "9.449534,9.881934,0.263957")
(COMMAND "POINT" "9.535378,9.909058,0.250584")
(COMMAND "POINT" "9.620768,9.939192,0.236803")
(COMMAND "POINT" "9.705228,9.970859,0.223274")
(COMMAND "POINT" "9.788680,10.003812,0.210107")
(COMMAND "POINT" "9.871122,10.038052,0.197302")
(COMMAND "POINT" "9.952555,10.073580,0.184860")
(COMMAND "POINT" "10.032979,10.110393,0.172780")
(COMMAND "POINT" "10.112394,10.148494,0.161063")
(COMMAND "POINT" "10.190800,10.187881,0.149707")
(COMMAND "POINT" "10.268196,10.228555,0.138715")
(COMMAND "POINT" "10.344583,10.270516,0.128084")
(COMMAND "POINT" "10.419962,10.313764,0.117816")
(COMMAND "POINT" "10.494331,10.358298,0.107910")
(COMMAND "POINT" "10.567690,10.404119,0.098367")
(COMMAND "POINT" "10.640041,10.451227,0.089186")
(COMMAND "POINT" "10.711383,10.499622,0.080367")
(COMMAND "POINT" "10.781715,10.549304,0.071911")
(COMMAND "POINT" "10.851038,10.600272,0.063817")
(COMMAND "POINT" "10.919353,10.652527,0.056086")
(COMMAND "POINT" "10.986658,10.706069,0.048716")
(COMMAND "POINT" "11.052953,10.760898,0.041709")
(COMMAND "POINT" "11.118240,10.817013,0.035065")
(COMMAND "POINT" "11.182517,10.874415,0.028783")
(COMMAND "POINT" "11.245786,10.933104,0.022863")
(COMMAND "POINT" "11.308045,10.993080,0.017306")
(COMMAND "POINT" "11.369295,11.054342,0.012111")
(COMMAND "POINT" "11.429536,11.116892,0.007278")
(COMMAND "POINT" "11.488768,11.180728,0.002807")
(COMMAND "POINT" "11.546990,11.245851,-0.001301")
(COMMAND "POINT" "11.604204,11.312260,-0.005046")
(COMMAND "POINT" "11.660408,11.379957,-0.008429")
(COMMAND "POINT" "11.715603,11.448940,-0.011450")
(COMMAND "POINT" "11.769789,11.519210,-0.014109")
(COMMAND "POINT" "11.822966,11.590766,-0.016405")
(COMMAND "POINT" "11.875134,11.663610,-0.018339")
(COMMAND "POINT" "11.926292,11.737740,-0.019910")
(COMMAND "POINT" "11.976441,11.813157,-0.021120")
(COMMAND "POINT" "12.025582,11.889861,-0.021966")
(COMMAND "POINT" "12.073713,11.967852,-0.022451")
(COMMAND "POINT" "12.120835,12.047129,-0.022573")
(COMMAND "POINT" "12.166947,12.127693,-0.022333")
(COMMAND "POINT" "12.212051,12.209544,-0.021730")
(COMMAND "POINT" "12.256145,12.292682,-0.020765")
(COMMAND "POINT" "12.299231,12.377106,-0.019438")
(COMMAND "POINT" "12.341307,12.462818,-0.017748")
(COMMAND "POINT" "12.382374,12.549816,-0.015696")
(COMMAND "POINT" "12.422432,12.638100,-0.013281")
(COMMAND "POINT" "12.461480,12.727672,-0.010505")
(COMMAND "POINT" "12.499520,12.818530,-0.007365")
(COMMAND "POINT" "12.536550,12.910675,-0.003864")
(COMMAND "POINT" "12.572571,13.004107,0.000000")
(COMMAND "POINT" "4.907645,12.580899,0.329362")
(COMMAND "POINT" "5.006695,12.453663,0.342214")
(COMMAND "POINT" "5.105514,12.329643,0.354488")
(COMMAND "POINT" "5.204104,12.208839,0.366183")
(COMMAND "POINT" "5.302462,12.091250,0.377301")
(COMMAND "POINT" "5.400591,11.976876,0.387840")
(COMMAND "POINT" "5.498489,11.865718,0.397801")
(COMMAND "POINT" "5.596157,11.757775,0.407184")
(COMMAND "POINT" "5.693594,11.653048,0.415989")
(COMMAND "POINT" "5.790801,11.551536,0.424215")
(COMMAND "POINT" "5.887778,11.453240,0.431864")
(COMMAND "POINT" "5.984525,11.358159,0.438934")
(COMMAND "POINT" "6.081041,11.266294,0.445426")
(COMMAND "POINT" "6.177326,11.177644,0.451340")
(COMMAND "POINT" "6.273382,11.092210,0.456676")
(COMMAND "POINT" "6.369207,11.009991,0.461434")
(COMMAND "POINT" "6.464802,10.930988,0.465613")
(COMMAND "POINT" "6.560166,10.855200,0.469215")
(COMMAND "POINT" "6.655300,10.782628,0.472238")
(COMMAND "POINT" "6.750204,10.713271,0.474683")
(COMMAND "POINT" "6.844877,10.647129,0.476550")
(COMMAND "POINT" "6.939320,10.584203,0.477839")
(COMMAND "POINT" "7.033533,10.524493,0.478549")
(COMMAND "POINT" "7.127515,10.467998,0.478682")
(COMMAND "POINT" "7.221267,10.414719,0.478236")
(COMMAND "POINT" "7.314789,10.364655,0.477212")
(COMMAND "POINT" "7.408080,10.317806,0.475610")
(COMMAND "POINT" "7.501141,10.274173,0.473430")
(COMMAND "POINT" "7.593972,10.233755,0.470672")
(COMMAND "POINT" "7.686572,10.196553,0.467335")
(COMMAND "POINT" "7.778942,10.162567,0.463421")
(COMMAND "POINT" "7.871082,10.131796,0.458928")
(COMMAND "POINT" "7.962991,10.104240,0.453857")
(COMMAND "POINT" "8.054670,10.079900,0.448208")
(COMMAND "POINT" "8.146119,10.058775,0.441981")
(COMMAND "POINT" "8.237337,10.040866,0.435175")
(COMMAND "POINT" "8.328325,10.026172,0.427792")
(COMMAND "POINT" "8.419082,10.014694,0.419830")
(COMMAND "POINT" "8.509610,10.006431,0.411290")
(COMMAND "POINT" "8.599907,10.001384,0.402172")
(COMMAND "POINT" "8.689973,9.999552,0.392476")
(COMMAND "POINT" "8.779809,10.000936,0.382202")
(COMMAND "POINT" "8.869415,10.005535,0.371349")
(COMMAND "POINT" "8.958791,10.013349,0.359919")
(COMMAND "POINT" "9.047936,10.024380,0.347910")
(COMMAND "POINT" "9.136851,10.038625,0.335323")
(COMMAND "POINT" "9.225535,10.056086,0.322158")
(COMMAND "POINT" "9.313990,10.076763,0.308415")
(COMMAND "POINT" "9.402213,10.100655,0.294093")
(COMMAND "POINT" "9.490207,10.127762,0.279194")
(COMMAND "POINT" "9.577871,10.157845,0.263839")
(COMMAND "POINT" "9.664608,10.189460,0.248765")
(COMMAND "POINT" "9.750321,10.222366,0.234095")
(COMMAND "POINT" "9.835008,10.256564,0.219828")
(COMMAND "POINT" "9.918670,10.292054,0.205966")
(COMMAND "POINT" "10.001306,10.328835,0.192506")
(COMMAND "POINT" "10.082917,10.366908,0.179451")
(COMMAND "POINT" "10.163503,10.406273,0.166800")
(COMMAND "POINT" "10.243063,10.446929,0.154552")
(COMMAND "POINT" "10.321598,10.488877,0.142708")
(COMMAND "POINT" "10.399108,10.532117,0.131267")
(COMMAND "POINT" "10.475592,10.576649,0.120231")
(COMMAND "POINT" "10.551051,10.622472,0.109598")
(COMMAND "POINT" "10.625485,10.669587,0.099368")
(COMMAND "POINT" "10.698893,10.717993,0.089543")
(COMMAND "POINT" "10.771276,10.767692,0.080121")
(COMMAND "POINT" "10.842633,10.818681,0.071103")
(COMMAND "POINT" "10.912966,10.870963,0.062489")
(COMMAND "POINT" "10.982273,10.924536,0.054278")
(COMMAND "POINT" "11.050554,10.979401,0.046471")
(COMMAND "POINT" "11.117810,11.035558,0.039068")
(COMMAND "POINT" "11.184041,11.093006,0.032069")
(COMMAND "POINT" "11.249246,11.151746,0.025473")
(COMMAND "POINT" "11.313426,11.211778,0.019281")
(COMMAND "POINT" "11.376581,11.273101,0.013493")
(COMMAND "POINT" "11.438711,11.335716,0.008109")
(COMMAND "POINT" "11.499815,11.399623,0.003128")
(COMMAND "POINT" "11.559893,11.464821,-0.001449")
(COMMAND "POINT" "11.618947,11.531311,-0.005622")
(COMMAND "POINT" "11.676975,11.599093,-0.009392")
(COMMAND "POINT" "11.733977,11.668166,-0.012758")
(COMMAND "POINT" "11.789955,11.738532,-0.015720")
(COMMAND "POINT" "11.844906,11.810188,-0.018278")
(COMMAND "POINT" "11.898833,11.883137,-0.020433")
(COMMAND "POINT" "11.951734,11.957377,-0.022184")
(COMMAND "POINT" "12.003610,12.032909,-0.023531")
(COMMAND "POINT" "12.054461,12.109732,-0.024474")
(COMMAND "POINT" "12.104286,12.187847,-0.025014")
(COMMAND "POINT" "12.153086,12.267254,-0.025150")
(COMMAND "POINT" "12.200860,12.347953,-0.024882")
(COMMAND "POINT" "12.247609,12.429943,-0.024211")
(COMMAND "POINT" "12.293333,12.513225,-0.023136")
(COMMAND "POINT" "12.338031,12.597799,-0.021657")
(COMMAND "POINT" "12.381704,12.683664,-0.019774")
(COMMAND "POINT" "12.424352,12.770821,-0.017488")
(COMMAND "POINT" "12.465975,12.859270,-0.014798")
(COMMAND "POINT" "12.506572,12.949010,-0.011704")
(COMMAND "POINT" "12.546143,13.040042,-0.008206")
(COMMAND "POINT" "12.584690,13.132366,-0.004305")
(COMMAND "POINT" "12.622210,13.225981,0.000000")
(COMMAND "POINT" "4.913762,12.743953,0.364398")
(COMMAND "POINT" "5.008550,12.619265,0.378617")
(COMMAND "POINT" "5.103243,12.497734,0.392197")
(COMMAND "POINT" "5.197842,12.379360,0.405136")
(COMMAND "POINT" "5.292346,12.264144,0.417436")
(COMMAND "POINT" "5.386755,12.152085,0.429097")
(COMMAND "POINT" "5.481069,12.043184,0.440117")
(COMMAND "POINT" "5.575289,11.937440,0.450498")
(COMMAND "POINT" "5.669414,11.834854,0.460240")
(COMMAND "POINT" "5.763444,11.735425,0.469341")
(COMMAND "POINT" "5.857379,11.639154,0.477803")
(COMMAND "POINT" "5.951220,11.546040,0.485626")
(COMMAND "POINT" "6.044966,11.456084,0.492809")
(COMMAND "POINT" "6.138617,11.369284,0.499352")
(COMMAND "POINT" "6.232174,11.285643,0.505255")
(COMMAND "POINT" "6.325636,11.205159,0.510519")
(COMMAND "POINT" "6.419003,11.127832,0.515143")
(COMMAND "POINT" "6.512275,11.053663,0.519128")
(COMMAND "POINT" "6.605453,10.982651,0.522472")
(COMMAND "POINT" "6.698536,10.914796,0.525178")
(COMMAND "POINT" "6.791524,10.850100,0.527243")
(COMMAND "POINT" "6.884418,10.788560,0.528669")
(COMMAND "POINT" "6.977217,10.730178,0.529455")
(COMMAND "POINT" "7.069921,10.674953,0.529602")
(COMMAND "POINT" "7.162530,10.622886,0.529109")
(COMMAND "POINT" "7.255045,10.573976,0.527976")
(COMMAND "POINT" "7.347465,10.528224,0.526203")
(COMMAND "POINT" "7.439790,10.485629,0.523791")
(COMMAND "POINT" "7.532021,10.446192,0.520740")
(COMMAND "POINT" "7.624156,10.409912,0.517048")
(COMMAND "POINT" "7.716197,10.376789,0.512717")
(COMMAND "POINT" "7.808144,10.346824,0.507747")
(COMMAND "POINT" "7.899995,10.320017,0.502136")
(COMMAND "POINT" "7.991752,10.296367,0.495886")
(COMMAND "POINT" "8.083414,10.275874,0.488997")
(COMMAND "POINT" "8.174982,10.258539,0.481467")
(COMMAND "POINT" "8.266454,10.244361,0.473298")
(COMMAND "POINT" "8.357832,10.233340,0.464490")
(COMMAND "POINT" "8.449116,10.225477,0.455041")
(COMMAND "POINT" "8.540304,10.220772,0.444954")
(COMMAND "POINT" "8.631398,10.219224,0.434226")
(COMMAND "POINT" "8.722397,10.220833,0.422859")
(COMMAND "POINT" "8.813302,10.225600,0.410852")
(COMMAND "POINT" "8.904111,10.233524,0.398205")
(COMMAND "POINT" "8.994826,10.244606,0.384919")
(COMMAND "POINT" "9.085446,10.258845,0.370993")
(COMMAND "POINT" "9.175972,10.276242,0.356428")
(COMMAND "POINT" "9.266403,10.296796,0.341223")
(COMMAND "POINT" "9.356739,10.320507,0.325378")
(COMMAND "POINT" "9.446980,10.347376,0.308893")
(COMMAND "POINT" "9.537009,10.377170,0.291905")
(COMMAND "POINT" "9.626117,10.408496,0.275228")
(COMMAND "POINT" "9.714186,10.441121,0.258997")
(COMMAND "POINT" "9.801216,10.475046,0.243213")
(COMMAND "POINT" "9.887207,10.510269,0.227875")
(COMMAND "POINT" "9.972160,10.546793,0.212984")
(COMMAND "POINT" "10.056074,10.584615,0.198540")
(COMMAND "POINT" "10.138949,10.623737,0.184543")
(COMMAND "POINT" "10.220785,10.664158,0.170992")
(COMMAND "POINT" "10.301582,10.705879,0.157888")
(COMMAND "POINT" "10.381341,10.748899,0.145231")
(COMMAND "POINT" "10.460061,10.793218,0.133020")
(COMMAND "POINT" "10.537742,10.838836,0.121256")
(COMMAND "POINT" "10.614384,10.885754,0.109939")
(COMMAND "POINT" "10.689987,10.933972,0.099068")
(COMMAND "POINT" "10.764552,10.983488,0.088644")
(COMMAND "POINT" "10.838078,11.034304,0.078667")
(COMMAND "POINT" "10.910565,11.086420,0.069136")
(COMMAND "POINT" "10.982013,11.139835,0.060052")
(COMMAND "POINT" "11.052423,11.194549,0.051415")
(COMMAND "POINT" "11.121793,11.250562,0.043224")
(COMMAND "POINT" "11.190125,11.307875,0.035480")
(COMMAND "POINT" "11.257418,11.366487,0.028183")
(COMMAND "POINT" "11.323672,11.426399,0.021332")
(COMMAND "POINT" "11.388888,11.487609,0.014929")
(COMMAND "POINT" "11.453064,11.550120,0.008971")
(COMMAND "POINT" "11.516202,11.613929,0.003461")
(COMMAND "POINT" "11.578301,11.679038,-0.001603")
(COMMAND "POINT" "11.639361,11.745446,-0.006220")
(COMMAND "POINT" "11.699383,11.813154,-0.010391")
(COMMAND "POINT" "11.758365,11.882161,-0.014115")
(COMMAND "POINT" "11.816309,11.952467,-0.017392")
(COMMAND "POINT" "11.873214,12.024073,-0.020222")
(COMMAND "POINT" "11.929081,12.096978,-0.022606")
(COMMAND "POINT" "11.983908,12.171183,-0.024543")
(COMMAND "POINT" "12.037697,12.246686,-0.026034")
(COMMAND "POINT" "12.090446,12.323489,-0.027078")
(COMMAND "POINT" "12.142157,12.401592,-0.027675")
(COMMAND "POINT" "12.192830,12.480994,-0.027825")
(COMMAND "POINT" "12.242463,12.561695,-0.027529")
(COMMAND "POINT" "12.291058,12.643695,-0.026786")
(COMMAND "POINT" "12.338614,12.726995,-0.025597")
(COMMAND "POINT" "12.385131,12.811595,-0.023961")
(COMMAND "POINT" "12.430609,12.897493,-0.021878")
(COMMAND "POINT" "12.475048,12.984691,-0.019348")
(COMMAND "POINT" "12.518449,13.073188,-0.016372")
(COMMAND "POINT" "12.560811,13.162985,-0.012949")
(COMMAND "POINT" "12.602134,13.254081,-0.009079")
(COMMAND "POINT" "12.642418,13.346476,-0.004763")
(COMMAND "POINT" "12.681663,13.440171,0.000000")
(COMMAND "POINT" "4.907948,12.897441,0.400720")
(COMMAND "POINT" "4.998943,12.775949,0.416357")
(COMMAND "POINT" "5.089971,12.657538,0.431289")
(COMMAND "POINT" "5.181032,12.542208,0.445519")
(COMMAND "POINT" "5.272126,12.429960,0.459045")
(COMMAND "POINT" "5.363254,12.320793,0.471867")
(COMMAND "POINT" "5.454414,12.214707,0.483987")
(COMMAND "POINT" "5.545608,12.111703,0.495402")
(COMMAND "POINT" "5.636835,12.011780,0.506115")
(COMMAND "POINT" "5.728095,11.914938,0.516124")
(COMMAND "POINT" "5.819388,11.821177,0.525429")
(COMMAND "POINT" "5.910714,11.730498,0.534031")
(COMMAND "POINT" "6.002074,11.642900,0.541930")
(COMMAND "POINT" "6.093467,11.558383,0.549125")
(COMMAND "POINT" "6.184893,11.476947,0.555617")
(COMMAND "POINT" "6.276352,11.398593,0.561406")
(COMMAND "POINT" "6.367844,11.323320,0.566491")
(COMMAND "POINT" "6.459369,11.251128,0.570872")
(COMMAND "POINT" "6.550928,11.182017,0.574551")
(COMMAND "POINT" "6.642520,11.115988,0.577525")
(COMMAND "POINT" "6.734145,11.053040,0.579797")
(COMMAND "POINT" "6.825803,10.993173,0.581365")
(COMMAND "POINT" "6.917494,10.936388,0.582229")
(COMMAND "POINT" "7.009219,10.882684,0.582391")
(COMMAND "POINT" "7.100976,10.832061,0.581848")
(COMMAND "POINT" "7.192767,10.784519,0.580603")
(COMMAND "POINT" "7.284591,10.740059,0.578654")
(COMMAND "POINT" "7.376448,10.698680,0.576001")
(COMMAND "POINT" "7.468338,10.660382,0.572645")
(COMMAND "POINT" "7.560262,10.625165,0.568586")
(COMMAND "POINT" "7.652219,10.593030,0.563823")
(COMMAND "POINT" "7.744208,10.563976,0.558357")
(COMMAND "POINT" "7.836231,10.538003,0.552187")
(COMMAND "POINT" "7.928288,10.515112,0.545314")
(COMMAND "POINT" "8.020377,10.495301,0.537738")
(COMMAND "POINT" "8.112499,10.478572,0.529458")
(COMMAND "POINT" "8.204655,10.464925,0.520475")
(COMMAND "POINT" "8.296844,10.454358,0.510788")
(COMMAND "POINT" "8.389066,10.446873,0.500398")
(COMMAND "POINT" "8.481321,10.442469,0.489305")
(COMMAND "POINT" "8.573610,10.441147,0.477508")
(COMMAND "POINT" "8.665931,10.442905,0.465008")
(COMMAND "POINT" "8.758286,10.447745,0.451804")
(COMMAND "POINT" "8.850674,10.455666,0.437897")
(COMMAND "POINT" "8.943095,10.466669,0.423287")
(COMMAND "POINT" "9.035549,10.480752,0.407973")
(COMMAND "POINT" "9.128036,10.497917,0.391955")
(COMMAND "POINT" "9.220557,10.518164,0.375235")
(COMMAND "POINT" "9.313111,10.541491,0.357810")
(COMMAND "POINT" "9.405698,10.567900,0.339683")
(COMMAND "POINT" "9.498182,10.597169,0.321001")
(COMMAND "POINT" "9.589753,10.627968,0.302661")
(COMMAND "POINT" "9.680274,10.660078,0.284813")
(COMMAND "POINT" "9.769746,10.693497,0.267455")
(COMMAND "POINT" "9.858168,10.728227,0.250589")
(COMMAND "POINT" "9.945540,10.764266,0.234214")
(COMMAND "POINT" "10.031863,10.801615,0.218330")
(COMMAND "POINT" "10.117137,10.840273,0.202938")
(COMMAND "POINT" "10.201361,10.880241,0.188036")
(COMMAND "POINT" "10.284536,10.921520,0.173626")
(COMMAND "POINT" "10.366661,10.964108,0.159707")
(COMMAND "POINT" "10.447736,11.008005,0.146279")
(COMMAND "POINT" "10.527762,11.053213,0.133343")
(COMMAND "POINT" "10.606739,11.099730,0.120897")
(COMMAND "POINT" "10.684666,11.147558,0.108943")
(COMMAND "POINT" "10.761544,11.196694,0.097480")
(COMMAND "POINT" "10.837372,11.247141,0.086508")
(COMMAND "POINT" "10.912150,11.298898,0.076027")
(COMMAND "POINT" "10.985879,11.351964,0.066038")
(COMMAND "POINT" "11.058559,11.406340,0.056540")
(COMMAND "POINT" "11.130189,11.462026,0.047533")
(COMMAND "POINT" "11.200770,11.519022,0.039017")
(COMMAND "POINT" "11.270301,11.577327,0.030992")
(COMMAND "POINT" "11.338782,11.636943,0.023459")
(COMMAND "POINT" "11.406215,11.697868,0.016417")
(COMMAND "POINT" "11.472597,11.760103,0.009866")
(COMMAND "POINT" "11.537930,11.823647,0.003806")
(COMMAND "POINT" "11.602214,11.888502,-0.001763")
(COMMAND "POINT" "11.665448,11.954666,-0.006840")
(COMMAND "POINT" "11.727633,12.022140,-0.011427")
(COMMAND "POINT" "11.788768,12.090924,-0.015522")
(COMMAND "POINT" "11.848853,12.161017,-0.019126")
(COMMAND "POINT" "11.907889,12.232421,-0.022238")
(COMMAND "POINT" "11.965876,12.305134,-0.024860")
(COMMAND "POINT" "12.022813,12.379157,-0.026990")
(COMMAND "POINT" "12.078701,12.454490,-0.028629")
(COMMAND "POINT" "12.133539,12.531133,-0.029777")
(COMMAND "POINT" "12.187328,12.609085,-0.030433")
(COMMAND "POINT" "12.240067,12.688347,-0.030599")
(COMMAND "POINT" "12.291756,12.768919,-0.030273")
(COMMAND "POINT" "12.342397,12.850801,-0.029456")
(COMMAND "POINT" "12.391987,12.933992,-0.028148")
(COMMAND "POINT" "12.440528,13.018494,-0.026349")
(COMMAND "POINT" "12.488020,13.104305,-0.024058")
(COMMAND "POINT" "12.534462,13.191426,-0.021277")
(COMMAND "POINT" "12.579855,13.279857,-0.018004")
(COMMAND "POINT" "12.624198,13.369597,-0.014240")
(COMMAND "POINT" "12.667491,13.460648,-0.009984")
(COMMAND "POINT" "12.709736,13.553008,-0.005238")
(COMMAND "POINT" "12.750930,13.646678,0.000000")
(COMMAND "POINT" "4.890204,13.041363,0.438328")
(COMMAND "POINT" "4.977874,12.923716,0.455432")
(COMMAND "POINT" "5.065697,12.809057,0.471766")
(COMMAND "POINT" "5.153674,12.697384,0.487331")
(COMMAND "POINT" "5.241804,12.588698,0.502127")
(COMMAND "POINT" "5.330087,12.482999,0.516153")
(COMMAND "POINT" "5.418524,12.380287,0.529409")
(COMMAND "POINT" "5.507114,12.280563,0.541896")
(COMMAND "POINT" "5.595858,12.183825,0.553614")
(COMMAND "POINT" "5.684754,12.090074,0.564562")
(COMMAND "POINT" "5.773804,11.999310,0.574741")
(COMMAND "POINT" "5.863008,11.911532,0.584151")
(COMMAND "POINT" "5.952364,11.826742,0.592791")
(COMMAND "POINT" "6.041874,11.744939,0.600661")
(COMMAND "POINT" "6.131538,11.666123,0.607762")
(COMMAND "POINT" "6.221354,11.590294,0.614094")
(COMMAND "POINT" "6.311325,11.517451,0.619656")
(COMMAND "POINT" "6.401448,11.447596,0.624449")
(COMMAND "POINT" "6.491725,11.380727,0.628473")
(COMMAND "POINT" "6.582155,11.316846,0.631727")
(COMMAND "POINT" "6.672738,11.255951,0.634211")
(COMMAND "POINT" "6.763475,11.198044,0.635926")
(COMMAND "POINT" "6.854365,11.143123,0.636872")
(COMMAND "POINT" "6.945408,11.091190,0.637048")
(COMMAND "POINT" "7.036605,11.042243,0.636455")
(COMMAND "POINT" "7.127955,10.996283,0.635093")
(COMMAND "POINT" "7.219459,10.953310,0.632961")
(COMMAND "POINT" "7.311115,10.913324,0.630059")
(COMMAND "POINT" "7.402926,10.876325,0.626388")
(COMMAND "POINT" "7.494889,10.842313,0.621948")
(COMMAND "POINT" "7.587006,10.811288,0.616738")
(COMMAND "POINT" "7.679276,10.783250,0.610759")
(COMMAND "POINT" "7.771699,10.758199,0.604011")
(COMMAND "POINT" "7.864276,10.736135,0.596493")
(COMMAND "POINT" "7.957006,10.717058,0.588205")
(COMMAND "POINT" "8.049890,10.700968,0.579148")
(COMMAND "POINT" "8.142927,10.687864,0.569322")
(COMMAND "POINT" "8.236117,10.677748,0.558726")
(COMMAND "POINT" "8.329460,10.670618,0.547361")
(COMMAND "POINT" "8.422957,10.666476,0.535227")
(COMMAND "POINT" "8.516607,10.665320,0.522323")
(COMMAND "POINT" "8.610411,10.667152,0.508649")
(COMMAND "POINT" "8.704368,10.671970,0.494206")
(COMMAND "POINT" "8.798478,10.679776,0.478994")
(COMMAND "POINT" "8.892741,10.690568,0.463012")
(COMMAND "POINT" "8.987158,10.704347,0.446261")
(COMMAND "POINT" "9.081728,10.721113,0.428740")
(COMMAND "POINT" "9.176452,10.740866,0.410450")
(COMMAND "POINT" "9.271329,10.763607,0.391391")
(COMMAND "POINT" "9.366359,10.789334,0.371562")
(COMMAND "POINT" "9.461391,10.817840,0.351127")
(COMMAND "POINT" "9.555517,10.847877,0.331066")
(COMMAND "POINT" "9.648586,10.879237,0.311543")
(COMMAND "POINT" "9.740597,10.911920,0.292556")
(COMMAND "POINT" "9.831551,10.945926,0.274107")
(COMMAND "POINT" "9.921447,10.981255,0.256195")
(COMMAND "POINT" "10.010286,11.017907,0.238821")
(COMMAND "POINT" "10.098067,11.055882,0.221983")
(COMMAND "POINT" "10.184791,11.095180,0.205684")
(COMMAND "POINT" "10.270458,11.135801,0.189921")
(COMMAND "POINT" "10.355067,11.177745,0.174696")
(COMMAND "POINT" "10.438618,11.221012,0.160008")
(COMMAND "POINT" "10.521113,11.265602,0.145857")
(COMMAND "POINT" "10.602549,11.311515,0.132243")
(COMMAND "POINT" "10.682929,11.358751,0.119167")
(COMMAND "POINT" "10.762250,11.407310,0.106628")
(COMMAND "POINT" "10.840515,11.457192,0.094627")
(COMMAND "POINT" "10.917722,11.508397,0.083163")
(COMMAND "POINT" "10.993871,11.560925,0.072236")
(COMMAND "POINT" "11.068963,11.614776,0.061846")
(COMMAND "POINT" "11.142998,11.669950,0.051994")
(COMMAND "POINT" "11.215975,11.726447,0.042679")
(COMMAND "POINT" "11.287895,11.784267,0.033901")
(COMMAND "POINT" "11.358757,11.843410,0.025660")
(COMMAND "POINT" "11.428562,11.903876,0.017957")
(COMMAND "POINT" "11.497309,11.965665,0.010791")
(COMMAND "POINT" "11.564999,12.028777,0.004163")
(COMMAND "POINT" "11.631631,12.093212,-0.001928")
(COMMAND "POINT" "11.697206,12.158970,-0.007482")
(COMMAND "POINT" "11.761724,12.226051,-0.012499")
(COMMAND "POINT" "11.825184,12.294455,-0.016978")
(COMMAND "POINT" "11.887587,12.364182,-0.020920")
(COMMAND "POINT" "11.948932,12.435232,-0.024325")
(COMMAND "POINT" "12.009220,12.507605,-0.027193")
(COMMAND "POINT" "12.068450,12.581301,-0.029523")
(COMMAND "POINT" "12.126623,12.656320,-0.031316")
(COMMAND "POINT" "12.183738,12.732662,-0.032571")
(COMMAND "POINT" "12.239796,12.810327,-0.033290")
(COMMAND "POINT" "12.294797,12.889315,-0.033471")
(COMMAND "POINT" "12.348740,12.969626,-0.033114")
(COMMAND "POINT" "12.401625,13.051260,-0.032221")
(COMMAND "POINT" "12.453454,13.134217,-0.030790")
(COMMAND "POINT" "12.504224,13.218497,-0.028822")
(COMMAND "POINT" "12.553938,13.304100,-0.026316")
(COMMAND "POINT" "12.602594,13.391026,-0.023273")
(COMMAND "POINT" "12.650192,13.479275,-0.019693")
(COMMAND "POINT" "12.696733,13.568847,-0.015576")
(COMMAND "POINT" "12.742216,13.659742,-0.010921")
(COMMAND "POINT" "12.786642,13.751960,-0.005729")
(COMMAND "POINT" "12.830011,13.845501,0.000000")
(COMMAND "POINT" "4.860529,13.175719,0.477222")
(COMMAND "POINT" "4.945343,13.062567,0.495843")
(COMMAND "POINT" "5.030423,12.952289,0.513627")
(COMMAND "POINT" "5.115768,12.844886,0.530573")
(COMMAND "POINT" "5.201379,12.740358,0.546681")
(COMMAND "POINT" "5.287256,12.638704,0.561952")
(COMMAND "POINT" "5.373399,12.539924,0.576385")
(COMMAND "POINT" "5.459808,12.444019,0.589980")
(COMMAND "POINT" "5.546482,12.350989,0.602737")
(COMMAND "POINT" "5.633422,12.260833,0.614657")
(COMMAND "POINT" "5.720628,12.173551,0.625739")
(COMMAND "POINT" "5.808100,12.089144,0.635983")
(COMMAND "POINT" "5.895837,12.007612,0.645390")
(COMMAND "POINT" "5.983840,11.928954,0.653959")
(COMMAND "POINT" "6.072109,11.853170,0.661690")
(COMMAND "POINT" "6.160644,11.780261,0.668584")
(COMMAND "POINT" "6.249445,11.710226,0.674640")
(COMMAND "POINT" "6.338511,11.643066,0.679858")
(COMMAND "POINT" "6.427843,11.578781,0.684238")
(COMMAND "POINT" "6.517441,11.517370,0.687781")
(COMMAND "POINT" "6.607305,11.458833,0.690486")
(COMMAND "POINT" "6.697434,11.403171,0.692353")
(COMMAND "POINT" "6.787829,11.350383,0.693383")
(COMMAND "POINT" "6.878490,11.300470,0.693575")
(COMMAND "POINT" "6.969417,11.253432,0.692929")
(COMMAND "POINT" "7.060610,11.209268,0.691446")
(COMMAND "POINT" "7.152068,11.167978,0.689124")
(COMMAND "POINT" "7.243792,11.129563,0.685966")
(COMMAND "POINT" "7.335782,11.094022,0.681969")
(COMMAND "POINT" "7.428038,11.061356,0.677135")
(COMMAND "POINT" "7.520559,11.031565,0.671463")
(COMMAND "POINT" "7.613346,11.004647,0.664953")
(COMMAND "POINT" "7.706399,10.980605,0.657606")
(COMMAND "POINT" "7.799718,10.959437,0.649421")
(COMMAND "POINT" "7.893303,10.941143,0.640398")
(COMMAND "POINT" "7.987153,10.925724,0.630537")
(COMMAND "POINT" "8.081269,10.913179,0.619839")
(COMMAND "POINT" "8.175651,10.903509,0.608303")
(COMMAND "POINT" "8.270299,10.896713,0.595930")
(COMMAND "POINT" "8.365212,10.892792,0.582718")
(COMMAND "POINT" "8.460391,10.891745,0.568669")
(COMMAND "POINT" "8.555836,10.893573,0.553783")
(COMMAND "POINT" "8.651547,10.898275,0.538058")
(COMMAND "POINT" "8.747524,10.905852,0.521496")
(COMMAND "POINT" "8.843766,10.916303,0.504096")
(COMMAND "POINT" "8.940274,10.929629,0.485859")
(COMMAND "POINT" "9.037048,10.945829,0.466783")
(COMMAND "POINT" "9.134088,10.964904,0.446871")
(COMMAND "POINT" "9.231393,10.986853,0.426120")
(COMMAND "POINT" "9.328964,11.011677,0.404532")
(COMMAND "POINT" "9.426635,11.039183,0.382283")
(COMMAND "POINT" "9.523410,11.068221,0.360442")
(COMMAND "POINT" "9.619121,11.098597,0.339186")
(COMMAND "POINT" "9.713770,11.130312,0.318515")
(COMMAND "POINT" "9.807357,11.163366,0.298429")
(COMMAND "POINT" "9.899881,11.197759,0.278928")
(COMMAND "POINT" "9.991342,11.233491,0.260012")
(COMMAND "POINT" "10.081740,11.270562,0.241680")
(COMMAND "POINT" "10.171076,11.308972,0.223934")
(COMMAND "POINT" "10.259349,11.348721,0.206773")
(COMMAND "POINT" "10.346560,11.389809,0.190197")
(COMMAND "POINT" "10.432708,11.432236,0.174205")
(COMMAND "POINT" "10.517793,11.476002,0.158799")
(COMMAND "POINT" "10.601815,11.521107,0.143978")
(COMMAND "POINT" "10.684775,11.567551,0.129741")
(COMMAND "POINT" "10.766673,11.615334,0.116090")
(COMMAND "POINT" "10.847507,11.664456,0.103023")
(COMMAND "POINT" "10.927279,11.714917,0.090542")
(COMMAND "POINT" "11.005989,11.766716,0.078645")
(COMMAND "POINT" "11.083635,11.819855,0.067334")
(COMMAND "POINT" "11.160219,11.874333,0.056607")
(COMMAND "POINT" "11.235741,11.930150,0.046466")
(COMMAND "POINT" "11.310200,11.987305,0.036909")
(COMMAND "POINT" "11.383596,12.045800,0.027937")
(COMMAND "POINT" "11.455929,12.105633,0.019551")
(COMMAND "POINT" "11.527200,12.166806,0.011749")
(COMMAND "POINT" "11.597408,12.229318,0.004532")
(COMMAND "POINT" "11.666554,12.293168,-0.002099")
(COMMAND "POINT" "11.734637,12.358358,-0.008146")
(COMMAND "POINT" "11.801657,12.424886,-0.013608")
(COMMAND "POINT" "11.867614,12.492754,-0.018485")
(COMMAND "POINT" "11.932509,12.561960,-0.022777")
(COMMAND "POINT" "11.996342,12.632505,-0.026484")
(COMMAND "POINT" "12.059111,12.704390,-0.029606")
(COMMAND "POINT" "12.120818,12.777613,-0.032143")
(COMMAND "POINT" "12.181463,12.852175,-0.034095")
(COMMAND "POINT" "12.241044,12.928077,-0.035462")
(COMMAND "POINT" "12.299563,13.005317,-0.036244")
(COMMAND "POINT" "12.357020,13.083896,-0.036441")
(COMMAND "POINT" "12.413414,13.163814,-0.036053")
(COMMAND "POINT" "12.468745,13.245072,-0.035080")
(COMMAND "POINT" "12.523013,13.327668,-0.033522")
(COMMAND "POINT" "12.576219,13.411603,-0.031379")
(COMMAND "POINT" "12.628362,13.496877,-0.028651")
(COMMAND "POINT" "12.679443,13.583490,-0.025339")
(COMMAND "POINT" "12.729460,13.671442,-0.021441")
(COMMAND "POINT" "12.778416,13.760733,-0.016958")
(COMMAND "POINT" "12.826308,13.851363,-0.011890")
(COMMAND "POINT" "12.873138,13.943332,-0.006238")
(COMMAND "POINT" "12.918906,14.036640,0.000000")
(COMMAND "POINT" "4.818923,13.300509,0.517401")
(COMMAND "POINT" "4.901350,13.192501,0.537591")
(COMMAND "POINT" "4.984147,13.087236,0.556872")
(COMMAND "POINT" "5.067314,12.984716,0.575244")
(COMMAND "POINT" "5.150852,12.884939,0.592709")
(COMMAND "POINT" "5.234760,12.787907,0.609265")
(COMMAND "POINT" "5.319039,12.693618,0.624913")
(COMMAND "POINT" "5.403688,12.602073,0.639653")
(COMMAND "POINT" "5.488708,12.513272,0.653484")
(COMMAND "POINT" "5.574098,12.427215,0.666408")
(COMMAND "POINT" "5.659859,12.343902,0.678423")
(COMMAND "POINT" "5.745991,12.263333,0.689530")
(COMMAND "POINT" "5.832492,12.185508,0.699728")
(COMMAND "POINT" "5.919365,12.110426,0.709019")
(COMMAND "POINT" "6.006607,12.038089,0.717401")
(COMMAND "POINT" "6.094221,11.968495,0.724875")
(COMMAND "POINT" "6.182204,11.901645,0.731441")
(COMMAND "POINT" "6.270559,11.837540,0.737098")
(COMMAND "POINT" "6.359283,11.776178,0.741847")
(COMMAND "POINT" "6.448379,11.717560,0.745688")
(COMMAND "POINT" "6.537844,11.661685,0.748621")
(COMMAND "POINT" "6.627680,11.608555,0.750646")
(COMMAND "POINT" "6.717887,11.558169,0.751762")
(COMMAND "POINT" "6.808464,11.510526,0.751970")
(COMMAND "POINT" "6.899412,11.465628,0.751270")
(COMMAND "POINT" "6.990730,11.423473,0.749662")
(COMMAND "POINT" "7.082419,11.384062,0.747145")
(COMMAND "POINT" "7.174478,11.347396,0.743720")
(COMMAND "POINT" "7.266908,11.313473,0.739387")
(COMMAND "POINT" "7.359708,11.282294,0.734146")
(COMMAND "POINT" "7.452878,11.253858,0.727996")
(COMMAND "POINT" "7.546420,11.228167,0.720939")
(COMMAND "POINT" "7.640331,11.205220,0.712973")
(COMMAND "POINT" "7.734613,11.185016,0.704098")
(COMMAND "POINT" "7.829266,11.167557,0.694316")
(COMMAND "POINT" "7.924289,11.152841,0.683625")
(COMMAND "POINT" "8.019683,11.140869,0.672026")
(COMMAND "POINT" "8.115447,11.131641,0.659519")
(COMMAND "POINT" "8.211581,11.125157,0.646104")
(COMMAND "POINT" "8.308086,11.121417,0.631780")
(COMMAND "POINT" "8.404962,11.120421,0.616548")
(COMMAND "POINT" "8.502208,11.122169,0.600408")
(COMMAND "POINT" "8.599824,11.126660,0.583360")
(COMMAND "POINT" "8.697811,11.133896,0.565403")
(COMMAND "POINT" "8.796169,11.143875,0.546538")
(COMMAND "POINT" "8.894897,11.156599,0.526765")
(COMMAND "POINT" "8.993995,11.172066,0.506084")
(COMMAND "POINT" "9.093464,11.190277,0.484495")
(COMMAND "POINT" "9.193304,11.211232,0.461997")
(COMMAND "POINT" "9.293514,11.234931,0.438591")
(COMMAND "POINT" "9.393915,11.261200,0.414470")
(COMMAND "POINT" "9.493430,11.289001,0.390790")
(COMMAND "POINT" "9.591881,11.318159,0.367744")
(COMMAND "POINT" "9.689266,11.348675,0.345332")
(COMMAND "POINT" "9.785586,11.380548,0.323555")
(COMMAND "POINT" "9.880841,11.413780,0.302412")
(COMMAND "POINT" "9.975031,11.448369,0.281903")
(COMMAND "POINT" "10.068156,11.484316,0.262029")
(COMMAND "POINT" "10.160215,11.521620,0.242788")
(COMMAND "POINT" "10.251210,11.560282,0.224182")
(COMMAND "POINT" "10.341139,11.600302,0.206210")
(COMMAND "POINT" "10.430004,11.641680,0.188873")
(COMMAND "POINT" "10.517803,11.684415,0.172169")
(COMMAND "POINT" "10.604537,11.728508,0.156100")
(COMMAND "POINT" "10.690206,11.773959,0.140665")
(COMMAND "POINT" "10.774810,11.820767,0.125864")
(COMMAND "POINT" "10.858349,11.868934,0.111697")
(COMMAND "POINT" "10.940823,11.918458,0.098165")
(COMMAND "POINT" "11.022232,11.969339,0.085267")
(COMMAND "POINT" "11.102575,12.021579,0.073003")
(COMMAND "POINT" "11.181854,12.075176,0.061373")
(COMMAND "POINT" "11.260067,12.130130,0.050378")
(COMMAND "POINT" "11.337216,12.186443,0.040017")
(COMMAND "POINT" "11.413299,12.244113,0.030290")
(COMMAND "POINT" "11.488317,12.303141,0.021197")
(COMMAND "POINT" "11.562270,12.363527,0.012738")
(COMMAND "POINT" "11.635158,12.425270,0.004914")
(COMMAND "POINT" "11.706981,12.488371,-0.002276")
(COMMAND "POINT" "11.777739,12.552830,-0.008832")
(COMMAND "POINT" "11.847431,12.618646,-0.014754")
(COMMAND "POINT" "11.916059,12.685821,-0.020041")
(COMMAND "POINT" "11.983621,12.754352,-0.024694")
(COMMAND "POINT" "12.050119,12.824242,-0.028713")
(COMMAND "POINT" "12.115551,12.895489,-0.032098")
(COMMAND "POINT" "12.179918,12.968095,-0.034849")
(COMMAND "POINT" "12.243220,13.042057,-0.036965")
(COMMAND "POINT" "12.305457,13.117378,-0.038447")
(COMMAND "POINT" "12.366629,13.194056,-0.039295")
(COMMAND "POINT" "12.426736,13.272092,-0.039509")
(COMMAND "POINT" "12.485777,13.351486,-0.039088")
(COMMAND "POINT" "12.543754,13.432237,-0.038033")
(COMMAND "POINT" "12.600666,13.514346,-0.036344")
(COMMAND "POINT" "12.656512,13.597813,-0.034021")
(COMMAND "POINT" "12.711293,13.682637,-0.031064")
(COMMAND "POINT" "12.765009,13.768819,-0.027472")
(COMMAND "POINT" "12.817661,13.856359,-0.023246")
(COMMAND "POINT" "12.869247,13.945257,-0.018386")
(COMMAND "POINT" "12.919767,14.035512,-0.012891")
(COMMAND "POINT" "12.969223,14.127125,-0.006763")
(COMMAND "POINT" "13.017614,14.220096,0.000000")
(COMMAND "POINT" "4.765387,13.415733,0.558867")
(COMMAND "POINT" "4.845894,13.313518,0.580674")
(COMMAND "POINT" "4.926869,13.213897,0.601500")
(COMMAND "POINT" "5.008312,13.116873,0.621345")
(COMMAND "POINT" "5.090222,13.022443,0.640209")
(COMMAND "POINT" "5.172599,12.930608,0.658093")
(COMMAND "POINT" "5.255444,12.841369,0.674995")
(COMMAND "POINT" "5.338756,12.754724,0.690916")
(COMMAND "POINT" "5.422536,12.670675,0.705856")
(COMMAND "POINT" "5.506783,12.589221,0.719815")
(COMMAND "POINT" "5.591498,12.510363,0.732793")
(COMMAND "POINT" "5.676680,12.434099,0.744790")
(COMMAND "POINT" "5.762330,12.360430,0.755806")
(COMMAND "POINT" "5.848447,12.289357,0.765841")
(COMMAND "POINT" "5.935032,12.220879,0.774895")
(COMMAND "POINT" "6.022084,12.154996,0.782968")
(COMMAND "POINT" "6.109604,12.091708,0.790060")
(COMMAND "POINT" "6.197591,12.031015,0.796170")
(COMMAND "POINT" "6.286045,11.972918,0.801300")
(COMMAND "POINT" "6.374967,11.917416,0.805449")
(COMMAND "POINT" "6.464357,11.864508,0.808617")
(COMMAND "POINT" "6.554214,11.814196,0.810804")
(COMMAND "POINT" "6.644538,11.766479,0.812010")
(COMMAND "POINT" "6.735330,11.721358,0.812234")
(COMMAND "POINT" "6.826590,11.678831,0.811478")
(COMMAND "POINT" "6.918317,11.638900,0.809741")
(COMMAND "POINT" "7.010511,11.601563,0.807022")
(COMMAND "POINT" "7.103173,11.566822,0.803323")
(COMMAND "POINT" "7.196303,11.534676,0.798643")
(COMMAND "POINT" "7.289899,11.505126,0.792981")
(COMMAND "POINT" "7.383964,11.478170,0.786339")
(COMMAND "POINT" "7.478496,11.453810,0.778716")
(COMMAND "POINT" "7.573495,11.432044,0.770111")
(COMMAND "POINT" "7.668962,11.412874,0.760526")
(COMMAND "POINT" "7.764896,11.396299,0.749959")
(COMMAND "POINT" "7.861298,11.382319,0.738412")
(COMMAND "POINT" "7.958167,11.370935,0.725883")
(COMMAND "POINT" "8.055504,11.362145,0.712374")
(COMMAND "POINT" "8.153308,11.355951,0.697883")
(COMMAND "POINT" "8.251579,11.352352,0.682412")
(COMMAND "POINT" "8.350319,11.351348,0.665959")
(COMMAND "POINT" "8.449525,11.352939,0.648526")
(COMMAND "POINT" "8.549199,11.357125,0.630111")
(COMMAND "POINT" "8.649341,11.363907,0.610716")
(COMMAND "POINT" "8.749950,11.373283,0.590339")
(COMMAND "POINT" "8.851027,11.385255,0.568981")
(COMMAND "POINT" "8.952571,11.399822,0.546643")
(COMMAND "POINT" "9.054582,11.416984,0.523323")
(COMMAND "POINT" "9.157061,11.436742,0.499022")
(COMMAND "POINT" "9.260007,11.459094,0.473740")
(COMMAND "POINT" "9.363230,11.483890,0.447686")
(COMMAND "POINT" "9.465579,11.510216,0.422108")
(COMMAND "POINT" "9.566863,11.537922,0.397216")
(COMMAND "POINT" "9.667083,11.567008,0.373008")
(COMMAND "POINT" "9.766238,11.597472,0.349485")
(COMMAND "POINT" "9.864328,11.629316,0.326648")
(COMMAND "POINT" "9.961353,11.662539,0.304496")
(COMMAND "POINT" "10.057313,11.697141,0.283028")
(COMMAND "POINT" "10.152209,11.733122,0.262246")
(COMMAND "POINT" "10.246039,11.770483,0.242148")
(COMMAND "POINT" "10.338805,11.809223,0.222736")
(COMMAND "POINT" "10.430507,11.849342,0.204009")
(COMMAND "POINT" "10.521143,11.890840,0.185967")
(COMMAND "POINT" "10.610715,11.933717,0.168610")
(COMMAND "POINT" "10.699221,11.977974,0.151938")
(COMMAND "POINT" "10.786663,12.023610,0.135951")
(COMMAND "POINT" "10.873040,12.070625,0.120649")
(COMMAND "POINT" "10.958353,12.119020,0.106032")
(COMMAND "POINT" "11.042600,12.168793,0.092100")
(COMMAND "POINT" "11.125783,12.219946,0.078854")
(COMMAND "POINT" "11.207901,12.272478,0.066292")
(COMMAND "POINT" "11.288954,12.326389,0.054415")
(COMMAND "POINT" "11.368943,12.381680,0.043224")
(COMMAND "POINT" "11.447866,12.438349,0.032717")
(COMMAND "POINT" "11.525725,12.496398,0.022896")
(COMMAND "POINT" "11.602519,12.555827,0.013759")
(COMMAND "POINT" "11.678248,12.616634,0.005308")
(COMMAND "POINT" "11.752913,12.678820,-0.002459")
(COMMAND "POINT" "11.826512,12.742386,-0.009540")
(COMMAND "POINT" "11.899047,12.807331,-0.015936")
(COMMAND "POINT" "11.970517,12.873656,-0.021647")
(COMMAND "POINT" "12.040923,12.941359,-0.026674")
(COMMAND "POINT" "12.110263,13.010442,-0.031015")
(COMMAND "POINT" "12.178539,13.080904,-0.034671")
(COMMAND "POINT" "12.245749,13.152745,-0.037642")
(COMMAND "POINT" "12.311895,13.225965,-0.039928")
(COMMAND "POINT" "12.376977,13.300565,-0.041528")
(COMMAND "POINT" "12.440993,13.376544,-0.042444")
(COMMAND "POINT" "12.503945,13.453902,-0.042675")
(COMMAND "POINT" "12.565832,13.532639,-0.042221")
(COMMAND "POINT" "12.626654,13.612755,-0.041081")
(COMMAND "POINT" "12.686411,13.694251,-0.039257")
(COMMAND "POINT" "12.745103,13.777126,-0.036748")
(COMMAND "POINT" "12.802731,13.861380,-0.033553")
(COMMAND "POINT" "12.859294,13.947014,-0.029674")
(COMMAND "POINT" "12.914792,14.034026,-0.025109")
(COMMAND "POINT" "12.969225,14.122418,-0.019859")
(COMMAND "POINT" "13.022594,14.212189,-0.013925")
(COMMAND "POINT" "13.074897,14.303339,-0.007305")
(COMMAND "POINT" "13.126136,14.395869,0.000000")
(COMMAND "POINT" "4.699920,13.521391,0.601618")
(COMMAND "POINT" "4.778977,13.425618,0.625093")
(COMMAND "POINT" "4.858591,13.332273,0.647513")
(COMMAND "POINT" "4.938761,13.241356,0.668876")
(COMMAND "POINT" "5.019489,13.152868,0.689183")
(COMMAND "POINT" "5.100773,13.066808,0.708434")
(COMMAND "POINT" "5.182614,12.983176,0.726629")
(COMMAND "POINT" "5.265011,12.901973,0.743768")
(COMMAND "POINT" "5.347965,12.823198,0.759851")
(COMMAND "POINT" "5.431476,12.746851,0.774878")
(COMMAND "POINT" "5.515544,12.672932,0.788849")
(COMMAND "POINT" "5.600169,12.601442,0.801764")
(COMMAND "POINT" "5.685350,12.532380,0.813622")
(COMMAND "POINT" "5.771088,12.465746,0.824425")
(COMMAND "POINT" "5.857383,12.401541,0.834171")
(COMMAND "POINT" "5.944234,12.339763,0.842862")
(COMMAND "POINT" "6.031642,12.280415,0.850496")
(COMMAND "POINT" "6.119607,12.223494,0.857075")
(COMMAND "POINT" "6.208129,12.169002,0.862597")
(COMMAND "POINT" "6.297207,12.116938,0.867063")
(COMMAND "POINT" "6.386843,12.067302,0.870473")
(COMMAND "POINT" "6.477035,12.020094,0.872827")
(COMMAND "POINT" "6.567783,11.975315,0.874125")
(COMMAND "POINT" "6.659089,11.932964,0.874367")
(COMMAND "POINT" "6.750951,11.893042,0.873553")
(COMMAND "POINT" "6.843370,11.855547,0.871683")
(COMMAND "POINT" "6.936345,11.820481,0.868757")
(COMMAND "POINT" "7.029878,11.787843,0.864774")
(COMMAND "POINT" "7.123967,11.757634,0.859736")
(COMMAND "POINT" "7.218613,11.729853,0.853642")
(COMMAND "POINT" "7.313815,11.704500,0.846491")
(COMMAND "POINT" "7.409574,11.681575,0.838285")
(COMMAND "POINT" "7.505891,11.661079,0.829022")
(COMMAND "POINT" "7.602763,11.643010,0.818703")
(COMMAND "POINT" "7.700193,11.627371,0.807329")
(COMMAND "POINT" "7.798179,11.614159,0.794898")
(COMMAND "POINT" "7.896722,11.603376,0.781411")
(COMMAND "POINT" "7.995822,11.595021,0.766868")
(COMMAND "POINT" "8.095479,11.589094,0.751269")
(COMMAND "POINT" "8.195692,11.585596,0.734614")
(COMMAND "POINT" "8.296462,11.584526,0.716903")
(COMMAND "POINT" "8.397789,11.585884,0.698136")
(COMMAND "POINT" "8.499672,11.589670,0.678312")
(COMMAND "POINT" "8.602112,11.595885,0.657433")
(COMMAND "POINT" "8.705109,11.604528,0.635498")
(COMMAND "POINT" "8.808663,11.615599,0.612506")
(COMMAND "POINT" "8.912773,11.629099,0.588459")
(COMMAND "POINT" "9.017441,11.645027,0.563355")
(COMMAND "POINT" "9.122664,11.663383,0.537196")
(COMMAND "POINT" "9.228445,11.684167,0.509980")
(COMMAND "POINT" "9.334580,11.707252,0.481932")
(COMMAND "POINT" "9.439856,11.731868,0.454398")
(COMMAND "POINT" "9.544070,11.757888,0.427601")
(COMMAND "POINT" "9.647222,11.785311,0.401542")
(COMMAND "POINT" "9.749312,11.814137,0.376220")
(COMMAND "POINT" "9.850341,11.844368,0.351635")
(COMMAND "POINT" "9.950308,11.876001,0.327788")
(COMMAND "POINT" "10.049213,11.909039,0.304679")
(COMMAND "POINT" "10.147057,11.943479,0.282307")
(COMMAND "POINT" "10.243838,11.979323,0.260672")
(COMMAND "POINT" "10.339558,12.016571,0.239775")
(COMMAND "POINT" "10.434216,12.055222,0.219615")
(COMMAND "POINT" "10.527813,12.095277,0.200193")
(COMMAND "POINT" "10.620348,12.136735,0.181508")
(COMMAND "POINT" "10.711820,12.179597,0.163561")
(COMMAND "POINT" "10.802232,12.223862,0.146351")
(COMMAND "POINT" "10.891581,12.269530,0.129878")
(COMMAND "POINT" "10.979869,12.316603,0.114143")
(COMMAND "POINT" "11.067095,12.365078,0.099146")
(COMMAND "POINT" "11.153259,12.414957,0.084886")
(COMMAND "POINT" "11.238361,12.466240,0.071363")
(COMMAND "POINT" "11.322402,12.518926,0.058578")
(COMMAND "POINT" "11.405381,12.573016,0.046530")
(COMMAND "POINT" "11.487298,12.628509,0.035220")
(COMMAND "POINT" "11.568154,12.685406,0.024647")
(COMMAND "POINT" "11.647947,12.743706,0.014812")
(COMMAND "POINT" "11.726679,12.803409,0.005714")
(COMMAND "POINT" "11.804350,12.864516,-0.002647")
(COMMAND "POINT" "11.880958,12.927027,-0.010270")
(COMMAND "POINT" "11.956505,12.990941,-0.017155")
(COMMAND "POINT" "12.030990,13.056259,-0.023303")
(COMMAND "POINT" "12.104413,13.122980,-0.028714")
(COMMAND "POINT" "12.176775,13.191104,-0.033387")
(COMMAND "POINT" "12.248074,13.260633,-0.037323")
(COMMAND "POINT" "12.318312,13.331564,-0.040521")
(COMMAND "POINT" "12.387489,13.403899,-0.042982")
(COMMAND "POINT" "12.455603,13.477638,-0.044705")
(COMMAND "POINT" "12.522656,13.552780,-0.045691")
(COMMAND "POINT" "12.588647,13.629325,-0.045939")
(COMMAND "POINT" "12.653576,13.707275,-0.045450")
(COMMAND "POINT" "12.717444,13.786627,-0.044224")
(COMMAND "POINT" "12.780249,13.867383,-0.042260")
(COMMAND "POINT" "12.841993,13.949543,-0.039559")
(COMMAND "POINT" "12.902676,14.033106,-0.036120")
(COMMAND "POINT" "12.962296,14.118072,-0.031943")
(COMMAND "POINT" "13.020855,14.204443,-0.027030")
(COMMAND "POINT" "13.078352,14.292216,-0.021378")
(COMMAND "POINT" "13.134787,14.381393,-0.014990")
(COMMAND "POINT" "13.190161,14.471974,-0.007864")
(COMMAND "POINT" "13.244472,14.563958,0.000000")
(COMMAND "POINT" "4.622522,13.617483,0.645655")
(COMMAND "POINT" "4.700598,13.528801,0.670849")
(COMMAND "POINT" "4.779311,13.442362,0.694909")
(COMMAND "POINT" "4.858663,13.358167,0.717836")
(COMMAND "POINT" "4.938653,13.276215,0.739630")
(COMMAND "POINT" "5.019282,13.196506,0.760290")
(COMMAND "POINT" "5.100548,13.119041,0.779817")
(COMMAND "POINT" "5.182453,13.043818,0.798210")
(COMMAND "POINT" "5.264997,12.970839,0.815471")
(COMMAND "POINT" "5.348178,12.900104,0.831597")
(COMMAND "POINT" "5.431998,12.831611,0.846591")
(COMMAND "POINT" "5.516456,12.765362,0.860451")
(COMMAND "POINT" "5.601552,12.701356,0.873178")
(COMMAND "POINT" "5.687287,12.639593,0.884771")
(COMMAND "POINT" "5.773660,12.580074,0.895231")
(COMMAND "POINT" "5.860671,12.522798,0.904557")
(COMMAND "POINT" "5.948321,12.467765,0.912751")
(COMMAND "POINT" "6.036608,12.414975,0.919810")
(COMMAND "POINT" "6.125535,12.364429,0.925737")
(COMMAND "POINT" "6.215099,12.316126,0.930530")
(COMMAND "POINT" "6.305301,12.270066,0.934190")
(COMMAND "POINT" "6.396142,12.226249,0.936716")
(COMMAND "POINT" "6.487621,12.184676,0.938109")
(COMMAND "POINT" "6.579739,12.145346,0.938369")
(COMMAND "POINT" "6.672495,12.108259,0.937495")
(COMMAND "POINT" "6.765889,12.073415,0.935488")
(COMMAND "POINT" "6.859921,12.040815,0.932348")
(COMMAND "POINT" "6.954591,12.010458,0.928074")
(COMMAND "POINT" "7.049900,11.982344,0.922667")
(COMMAND "POINT" "7.145847,11.956474,0.916126")
(COMMAND "POINT" "7.242433,11.932847,0.908452")
(COMMAND "POINT" "7.339656,11.911463,0.899645")
(COMMAND "POINT" "7.437518,11.892322,0.889705")
(COMMAND "POINT" "7.536018,11.875425,0.878631")
(COMMAND "POINT" "7.635157,11.860771,0.866423")
(COMMAND "POINT" "7.734933,11.848360,0.853083")
(COMMAND "POINT" "7.835348,11.838192,0.838608")
(COMMAND "POINT" "7.936402,11.830268,0.823001")
(COMMAND "POINT" "8.038093,11.824587,0.806260")
(COMMAND "POINT" "8.140423,11.821149,0.788386")
(COMMAND "POINT" "8.243391,11.819954,0.769378")
(COMMAND "POINT" "8.346998,11.821003,0.749238")
(COMMAND "POINT" "8.451242,11.824295,0.727963")
(COMMAND "POINT" "8.556125,11.829830,0.705556")
(COMMAND "POINT" "8.661647,11.837609,0.682015")
(COMMAND "POINT" "8.767806,11.847631,0.657340")
(COMMAND "POINT" "8.874604,11.859896,0.631533")
(COMMAND "POINT" "8.982040,11.874404,0.604591")
(COMMAND "POINT" "9.090114,11.891155,0.576517")
(COMMAND "POINT" "9.198827,11.910150,0.547309")
(COMMAND "POINT" "9.307966,11.931287,0.517209")
(COMMAND "POINT" "9.416261,11.953955,0.487659")
(COMMAND "POINT" "9.523500,11.978055,0.458901")
(COMMAND "POINT" "9.629683,12.003584,0.430934")
(COMMAND "POINT" "9.734810,12.030544,0.403758")
(COMMAND "POINT" "9.838881,12.058935,0.377374")
(COMMAND "POINT" "9.941896,12.088757,0.351782")
(COMMAND "POINT" "10.043856,12.120008,0.326981")
(COMMAND "POINT" "10.144759,12.152691,0.302971")
(COMMAND "POINT" "10.244606,12.186804,0.279753")
(COMMAND "POINT" "10.343398,12.222347,0.257326")
(COMMAND "POINT" "10.441133,12.259321,0.235690")
(COMMAND "POINT" "10.537813,12.297726,0.214846")
(COMMAND "POINT" "10.633436,12.337561,0.194794")
(COMMAND "POINT" "10.728004,12.378827,0.175533")
(COMMAND "POINT" "10.821515,12.421523,0.157063")
(COMMAND "POINT" "10.913971,12.465649,0.139385")
(COMMAND "POINT" "11.005371,12.511207,0.122498")
(COMMAND "POINT" "11.095715,12.558194,0.106403")
(COMMAND "POINT" "11.185003,12.606613,0.091099")
(COMMAND "POINT" "11.273234,12.656462,0.076587")
(COMMAND "POINT" "11.360410,12.707741,0.062865")
(COMMAND "POINT" "11.446530,12.760451,0.049936")
(COMMAND "POINT" "11.531595,12.814591,0.037798")
(COMMAND "POINT" "11.615603,12.870162,0.026451")
(COMMAND "POINT" "11.698555,12.927164,0.015896")
(COMMAND "POINT" "11.780451,12.985596,0.006132")
(COMMAND "POINT" "11.861291,13.045459,-0.002840")
(COMMAND "POINT" "11.941076,13.106752,-0.011021")
(COMMAND "POINT" "12.019804,13.169476,-0.018411")
(COMMAND "POINT" "12.097476,13.233630,-0.025009")
(COMMAND "POINT" "12.174093,13.299215,-0.030816")
(COMMAND "POINT" "12.249653,13.366230,-0.035831")
(COMMAND "POINT" "12.324158,13.434676,-0.040055")
(COMMAND "POINT" "12.397607,13.504552,-0.043487")
(COMMAND "POINT" "12.469999,13.575859,-0.046128")
(COMMAND "POINT" "12.541336,13.648597,-0.047978")
(COMMAND "POINT" "12.611617,13.722765,-0.049036")
(COMMAND "POINT" "12.680842,13.798363,-0.049302")
(COMMAND "POINT" "12.749011,13.875392,-0.048777")
(COMMAND "POINT" "12.816124,13.953852,-0.047461")
(COMMAND "POINT" "12.882181,14.033742,-0.045353")
(COMMAND "POINT" "12.947182,14.115063,-0.042454")
(COMMAND "POINT" "13.011127,14.197814,-0.038764")
(COMMAND "POINT" "13.074016,14.281996,-0.034282")
(COMMAND "POINT" "13.135849,14.367608,-0.029008")
(COMMAND "POINT" "13.196626,14.454651,-0.022943")
(COMMAND "POINT" "13.256348,14.543125,-0.016087")
(COMMAND "POINT" "13.315013,14.633029,-0.008439")
(COMMAND "POINT" "13.372622,14.724363,0.000000")
(COMMAND "POINT" "4.534860,13.705117,0.690912")
(COMMAND "POINT" "4.612342,13.624094,0.717871")
(COMMAND "POINT" "4.690537,13.545112,0.743618")
(COMMAND "POINT" "4.769445,13.468172,0.768152")
(COMMAND "POINT" "4.849067,13.393275,0.791473")
(COMMAND "POINT" "4.929402,13.320420,0.813582")
(COMMAND "POINT" "5.010450,13.249607,0.834477")
(COMMAND "POINT" "5.092212,13.180836,0.854160")
(COMMAND "POINT" "5.174687,13.114108,0.872630")
(COMMAND "POINT" "5.257876,13.049422,0.889887")
(COMMAND "POINT" "5.341778,12.986777,0.905932")
(COMMAND "POINT" "5.426394,12.926176,0.920763")
(COMMAND "POINT" "5.511723,12.867616,0.934382")
(COMMAND "POINT" "5.597765,12.811098,0.946788")
(COMMAND "POINT" "5.684521,12.756623,0.957981")
(COMMAND "POINT" "5.771990,12.704190,0.967961")
(COMMAND "POINT" "5.860172,12.653799,0.976729")
(COMMAND "POINT" "5.949068,12.605450,0.984284")
(COMMAND "POINT" "6.038678,12.559143,0.990625")
(COMMAND "POINT" "6.129000,12.514879,0.995755")
(COMMAND "POINT" "6.220037,12.472657,0.999671")
(COMMAND "POINT" "6.311786,12.432477,1.002374")
(COMMAND "POINT" "6.404249,12.394339,1.003865")
(COMMAND "POINT" "6.497425,12.358243,1.004143")
(COMMAND "POINT" "6.591315,12.324190,1.003208")
(COMMAND "POINT" "6.685918,12.292179,1.001060")
(COMMAND "POINT" "6.781235,12.262210,0.997700")
(COMMAND "POINT" "6.877265,12.234283,0.993126")
(COMMAND "POINT" "6.974008,12.208398,0.987340")
(COMMAND "POINT" "7.071465,12.184556,0.980341")
(COMMAND "POINT" "7.169636,12.162756,0.972129")
(COMMAND "POINT" "7.268519,12.142997,0.962705")
(COMMAND "POINT" "7.368116,12.125282,0.952067")
(COMMAND "POINT" "7.468427,12.109608,0.940217")
(COMMAND "POINT" "7.569450,12.095976,0.927154")
(COMMAND "POINT" "7.671188,12.084387,0.912878")
(COMMAND "POINT" "7.773638,12.074840,0.897390")
(COMMAND "POINT" "7.876802,12.067335,0.880688")
(COMMAND "POINT" "7.980680,12.061872,0.862774")
(COMMAND "POINT" "8.085271,12.058452,0.843647")
(COMMAND "POINT" "8.190575,12.057074,0.823307")
(COMMAND "POINT" "8.296593,12.057737,0.801755")
(COMMAND "POINT" "8.403324,12.060443,0.778989")
(COMMAND "POINT" "8.510768,12.065192,0.755011")
(COMMAND "POINT" "8.618926,12.071982,0.729820")
(COMMAND "POINT" "8.727798,12.080815,0.703416")
(COMMAND "POINT" "8.837382,12.091690,0.675799")
(COMMAND "POINT" "8.947680,12.104607,0.646970")
(COMMAND "POINT" "9.058692,12.119566,0.616927")
(COMMAND "POINT" "9.170417,12.136567,0.585672")
(COMMAND "POINT" "9.282635,12.155538,0.553462")
(COMMAND "POINT" "9.394025,12.176042,0.521841")
(COMMAND "POINT" "9.504367,12.198005,0.491067")
(COMMAND "POINT" "9.613662,12.221428,0.461139")
(COMMAND "POINT" "9.721907,12.246312,0.432059")
(COMMAND "POINT" "9.829105,12.272655,0.403826")
(COMMAND "POINT" "9.935255,12.300458,0.376439")
(COMMAND "POINT" "10.040357,12.329721,0.349900")
(COMMAND "POINT" "10.144410,12.360444,0.324207")
(COMMAND "POINT" "10.247416,12.392627,0.299362")
(COMMAND "POINT" "10.349373,12.426270,0.275363")
(COMMAND "POINT" "10.450282,12.461373,0.252211")
(COMMAND "POINT" "10.550143,12.497936,0.229906")
(COMMAND "POINT" "10.648956,12.535959,0.208448")
(COMMAND "POINT" "10.746721,12.575441,0.187837")
(COMMAND "POINT" "10.843438,12.616384,0.168072")
(COMMAND "POINT" "10.939107,12.658786,0.149155")
(COMMAND "POINT" "11.033727,12.702649,0.131085")
(COMMAND "POINT" "11.127300,12.747971,0.113861")
(COMMAND "POINT" "11.219824,12.794754,0.097484")
(COMMAND "POINT" "11.311300,12.842996,0.081955")
(COMMAND "POINT" "11.401728,12.892698,0.067272")
(COMMAND "POINT" "11.491108,12.943860,0.053436")
(COMMAND "POINT" "11.579440,12.996482,0.040447")
(COMMAND "POINT" "11.666724,13.050564,0.028305")
(COMMAND "POINT" "11.752960,13.106106,0.017010")
(COMMAND "POINT" "11.838148,13.163108,0.006562")
(COMMAND "POINT" "11.922287,13.221570,-0.003040")
(COMMAND "POINT" "12.005379,13.281492,-0.011794")
(COMMAND "POINT" "12.087422,13.342873,-0.019701")
(COMMAND "POINT" "12.168417,13.405715,-0.026762")
(COMMAND "POINT" "12.248364,13.470016,-0.032976")
(COMMAND "POINT" "12.327263,13.535778,-0.038343")
(COMMAND "POINT" "12.405114,13.602999,-0.042862")
(COMMAND "POINT" "12.481917,13.671681,-0.046535")
(COMMAND "POINT" "12.557672,13.741822,-0.049361")
(COMMAND "POINT" "12.632378,13.813423,-0.051340")
(COMMAND "POINT" "12.706037,13.886484,-0.052473")
(COMMAND "POINT" "12.778647,13.961005,-0.052758")
(COMMAND "POINT" "12.850209,14.036986,-0.052196")
(COMMAND "POINT" "12.920724,14.114427,-0.050788")
(COMMAND "POINT" "12.990190,14.193328,-0.048532")
(COMMAND "POINT" "13.058608,14.273689,-0.045430")
(COMMAND "POINT" "13.125978,14.355510,-0.041481")
(COMMAND "POINT" "13.192299,14.438790,-0.036685")
(COMMAND "POINT" "13.257573,14.523531,-0.031041")
(COMMAND "POINT" "13.321799,14.609731,-0.024551")
(COMMAND "POINT" "13.384976,14.697392,-0.017215")
(COMMAND "POINT" "13.447105,14.786512,-0.009031")
(COMMAND "POINT" "13.508187,14.877093,0.000000")
(COMMAND "POINT" "4.446934,13.790944,0.736988")
(COMMAND "POINT" "4.523725,13.717650,0.765746")
(COMMAND "POINT" "4.601306,13.646194,0.793210")
(COMMAND "POINT" "4.679678,13.576576,0.819380")
(COMMAND "POINT" "4.758839,13.508795,0.844257")
(COMMAND "POINT" "4.838790,13.442852,0.867839")
(COMMAND "POINT" "4.919532,13.378747,0.890128")
(COMMAND "POINT" "5.001063,13.316479,0.911124")
(COMMAND "POINT" "5.083385,13.256048,0.930826")
(COMMAND "POINT" "5.166496,13.197455,0.949234")
(COMMAND "POINT" "5.250398,13.140700,0.966348")
(COMMAND "POINT" "5.335090,13.085782,0.982169")
(COMMAND "POINT" "5.420571,13.032702,0.996696")
(COMMAND "POINT" "5.506843,12.981460,1.009929")
(COMMAND "POINT" "5.593905,12.932055,1.021869")
(COMMAND "POINT" "5.681757,12.884488,1.032515")
(COMMAND "POINT" "5.770399,12.838758,1.041867")
(COMMAND "POINT" "5.859831,12.794866,1.049925")
(COMMAND "POINT" "5.950053,12.752811,1.056690")
(COMMAND "POINT" "6.041065,12.712594,1.062161")
(COMMAND "POINT" "6.132867,12.674215,1.066339")
(COMMAND "POINT" "6.225459,12.637673,1.069223")
(COMMAND "POINT" "6.318841,12.602969,1.070813")
(COMMAND "POINT" "6.413014,12.570102,1.071109")
(COMMAND "POINT" "6.507976,12.539073,1.070112")
(COMMAND "POINT" "6.603729,12.509882,1.067821")
(COMMAND "POINT" "6.700271,12.482528,1.064236")
(COMMAND "POINT" "6.797604,12.457011,1.059358")
(COMMAND "POINT" "6.895726,12.433333,1.053186")
(COMMAND "POINT" "6.994639,12.411492,1.045720")
(COMMAND "POINT" "7.094341,12.391488,1.036961")
(COMMAND "POINT" "7.194834,12.373322,1.026907")
(COMMAND "POINT" "7.296117,12.356994,1.015561")
(COMMAND "POINT" "7.398190,12.342503,1.002920")
(COMMAND "POINT" "7.501053,12.329850,0.988986")
(COMMAND "POINT" "7.604705,12.319034,0.973758")
(COMMAND "POINT" "7.709148,12.310056,0.957237")
(COMMAND "POINT" "7.814381,12.302916,0.939421")
(COMMAND "POINT" "7.920405,12.297613,0.920312")
(COMMAND "POINT" "8.027218,12.294148,0.899910")
(COMMAND "POINT" "8.134821,12.292520,0.878213")
(COMMAND "POINT" "8.243214,12.292730,0.855223")
(COMMAND "POINT" "8.352397,12.294777,0.830940")
(COMMAND "POINT" "8.462371,12.298662,0.805362")
(COMMAND "POINT" "8.573134,12.304385,0.778491")
(COMMAND "POINT" "8.684687,12.311945,0.750327")
(COMMAND "POINT" "8.797031,12.321343,0.720868")
(COMMAND "POINT" "8.910165,12.332578,0.690116")
(COMMAND "POINT" "9.024088,12.345651,0.658070")
(COMMAND "POINT" "9.138802,12.360562,0.624731")
(COMMAND "POINT" "9.254076,12.377267,0.590372")
(COMMAND "POINT" "9.368538,12.395504,0.556642")
(COMMAND "POINT" "9.481956,12.415231,0.523816")
(COMMAND "POINT" "9.594333,12.436446,0.491893")
(COMMAND "POINT" "9.705667,12.459151,0.460873")
(COMMAND "POINT" "9.815958,12.483345,0.430757")
(COMMAND "POINT" "9.925207,12.509029,0.401544")
(COMMAND "POINT" "10.033414,12.536201,0.373235")
(COMMAND "POINT" "10.140578,12.564863,0.345829")
(COMMAND "POINT" "10.246700,12.595014,0.319326")
(COMMAND "POINT" "10.351779,12.626654,0.293727")
(COMMAND "POINT" "10.455816,12.659783,0.269031")
(COMMAND "POINT" "10.558810,12.694402,0.245238")
(COMMAND "POINT" "10.660762,12.730510,0.222349")
(COMMAND "POINT" "10.761672,12.768107,0.200363")
(COMMAND "POINT" "10.861539,12.807193,0.179281")
(COMMAND "POINT" "10.960364,12.847768,0.159102")
(COMMAND "POINT" "11.058146,12.889832,0.139827")
(COMMAND "POINT" "11.154885,12.933386,0.121454")
(COMMAND "POINT" "11.250583,12.978429,0.103986")
(COMMAND "POINT" "11.345238,13.024961,0.087420")
(COMMAND "POINT" "11.438850,13.072982,0.071758")
(COMMAND "POINT" "11.531420,13.122493,0.057000")
(COMMAND "POINT" "11.622948,13.173492,0.043145")
(COMMAND "POINT" "11.713433,13.225981,0.030193")
(COMMAND "POINT" "11.802875,13.279959,0.018144")
(COMMAND "POINT" "11.891276,13.335427,0.006999")
(COMMAND "POINT" "11.978633,13.392383,-0.003242")
(COMMAND "POINT" "12.064949,13.450829,-0.012581")
(COMMAND "POINT" "12.150222,13.510764,-0.021015")
(COMMAND "POINT" "12.234452,13.572188,-0.028547")
(COMMAND "POINT" "12.317640,13.635101,-0.035175")
(COMMAND "POINT" "12.399786,13.699503,-0.040900")
(COMMAND "POINT" "12.480889,13.765395,-0.045721")
(COMMAND "POINT" "12.560950,13.832776,-0.049639")
(COMMAND "POINT" "12.639968,13.901646,-0.052653")
(COMMAND "POINT" "12.717944,13.972005,-0.054764")
(COMMAND "POINT" "12.794877,14.043853,-0.055972")
(COMMAND "POINT" "12.870768,14.117191,-0.056276")
(COMMAND "POINT" "12.945616,14.192018,-0.055677")
(COMMAND "POINT" "13.019422,14.268334,-0.054175")
(COMMAND "POINT" "13.092186,14.346139,-0.051769")
(COMMAND "POINT" "13.163907,14.425433,-0.048460")
(COMMAND "POINT" "13.234586,14.506217,-0.044247")
(COMMAND "POINT" "13.304222,14.588489,-0.039131")
(COMMAND "POINT" "13.372816,14.672251,-0.033112")
(COMMAND "POINT" "13.440367,14.757503,-0.026189")
(COMMAND "POINT" "13.506876,14.844243,-0.018363")
(COMMAND "POINT" "13.572343,14.932472,-0.009633")
(COMMAND "POINT" "13.636767,15.022191,0.000000")
(COMMAND "POINT" "4.360410,13.876071,0.783819")
(COMMAND "POINT" "4.436333,13.810498,0.814404")
(COMMAND "POINT" "4.513127,13.746556,0.843613")
(COMMAND "POINT" "4.590790,13.684246,0.871446")
(COMMAND "POINT" "4.669322,13.623567,0.897903")
(COMMAND "POINT" "4.748724,13.564520,0.922985")
(COMMAND "POINT" "4.828995,13.507104,0.946690")
(COMMAND "POINT" "4.910136,13.451320,0.969020")
(COMMAND "POINT" "4.992147,13.397168,0.989973")
(COMMAND "POINT" "5.075027,13.344646,1.009551")
(COMMAND "POINT" "5.158776,13.293757,1.027753")
(COMMAND "POINT" "5.243395,13.244499,1.044579")
(COMMAND "POINT" "5.328884,13.196873,1.060029")
(COMMAND "POINT" "5.415242,13.150878,1.074103")
(COMMAND "POINT" "5.502470,13.106514,1.086801")
(COMMAND "POINT" "5.590567,13.063782,1.098124")
(COMMAND "POINT" "5.679534,13.022682,1.108070")
(COMMAND "POINT" "5.769370,12.983213,1.116641")
(COMMAND "POINT" "5.860076,12.945376,1.123836")
(COMMAND "POINT" "5.951651,12.909170,1.129654")
(COMMAND "POINT" "6.044096,12.874596,1.134097")
(COMMAND "POINT" "6.137411,12.841653,1.137164")
(COMMAND "POINT" "6.231595,12.810342,1.138855")
(COMMAND "POINT" "6.326648,12.780663,1.139171")
(COMMAND "POINT" "6.422571,12.752614,1.138110")
(COMMAND "POINT" "6.519364,12.726198,1.135674")
(COMMAND "POINT" "6.617026,12.701413,1.131861")
(COMMAND "POINT" "6.715557,12.678259,1.126673")
(COMMAND "POINT" "6.814959,12.656737,1.120108")
(COMMAND "POINT" "6.915229,12.636847,1.112168")
(COMMAND "POINT" "7.016370,12.618588,1.102852")
(COMMAND "POINT" "7.118379,12.601961,1.092160")
(COMMAND "POINT" "7.221259,12.586965,1.080093")
(COMMAND "POINT" "7.325008,12.573600,1.066649")
(COMMAND "POINT" "7.429626,12.561868,1.051829")
(COMMAND "POINT" "7.535114,12.551766,1.035634")
(COMMAND "POINT" "7.641471,12.543297,1.018062")
(COMMAND "POINT" "7.748698,12.536458,0.999115")
(COMMAND "POINT" "7.856795,12.531252,0.978792")
(COMMAND "POINT" "7.965761,12.527676,0.957093")
(COMMAND "POINT" "8.075596,12.525733,0.934018")
(COMMAND "POINT" "8.186301,12.525421,0.909567")
(COMMAND "POINT" "8.297876,12.526740,0.883740")
(COMMAND "POINT" "8.410320,12.529691,0.856538")
(COMMAND "POINT" "8.523634,12.534273,0.827959")
(COMMAND "POINT" "8.637817,12.540487,0.798005")
(COMMAND "POINT" "8.752870,12.548333,0.766674")
(COMMAND "POINT" "8.868792,12.557810,0.733968")
(COMMAND "POINT" "8.985584,12.568919,0.699886")
(COMMAND "POINT" "9.103246,12.581659,0.664428")
(COMMAND "POINT" "9.221538,12.596016,0.627886")
(COMMAND "POINT" "9.339029,12.611906,0.592013")
(COMMAND "POINT" "9.455481,12.629313,0.557101")
(COMMAND "POINT" "9.570893,12.648239,0.523149")
(COMMAND "POINT" "9.685265,12.668682,0.490159")
(COMMAND "POINT" "9.798597,12.690643,0.458129")
(COMMAND "POINT" "9.910890,12.714122,0.427059")
(COMMAND "POINT" "10.022144,12.739119,0.396951")
(COMMAND "POINT" "10.132357,12.765634,0.367804")
(COMMAND "POINT" "10.241531,12.793667,0.339617")
(COMMAND "POINT" "10.349666,12.823218,0.312391")
(COMMAND "POINT" "10.456760,12.854286,0.286126")
(COMMAND "POINT" "10.562815,12.886873,0.260821")
(COMMAND "POINT" "10.667830,12.920977,0.236478")
(COMMAND "POINT" "10.771806,12.956600,0.213095")
(COMMAND "POINT" "10.874742,12.993740,0.190673")
(COMMAND "POINT" "10.976638,13.032398,0.169212")
(COMMAND "POINT" "11.077495,13.072574,0.148712")
(COMMAND "POINT" "11.177312,13.114268,0.129172")
(COMMAND "POINT" "11.276089,13.157480,0.110593")
(COMMAND "POINT" "11.373827,13.202210,0.092975")
(COMMAND "POINT" "11.470525,13.248458,0.076318")
(COMMAND "POINT" "11.566183,13.296224,0.060622")
(COMMAND "POINT" "11.660802,13.345507,0.045886")
(COMMAND "POINT" "11.754381,13.396309,0.032111")
(COMMAND "POINT" "11.846920,13.448628,0.019297")
(COMMAND "POINT" "11.938420,13.502465,0.007444")
(COMMAND "POINT" "12.028879,13.557821,-0.003448")
(COMMAND "POINT" "12.118300,13.614694,-0.013380")
(COMMAND "POINT" "12.206680,13.673085,-0.022351")
(COMMAND "POINT" "12.294021,13.732994,-0.030361")
(COMMAND "POINT" "12.380323,13.794421,-0.037410")
(COMMAND "POINT" "12.465584,13.857365,-0.043498")
(COMMAND "POINT" "12.549806,13.921828,-0.048626")
(COMMAND "POINT" "12.632989,13.987809,-0.052793")
(COMMAND "POINT" "12.715131,14.055307,-0.055999")
(COMMAND "POINT" "12.796234,14.124323,-0.058244")
(COMMAND "POINT" "12.876298,14.194858,-0.059529")
(COMMAND "POINT" "12.955321,14.266910,-0.059852")
(COMMAND "POINT" "13.033305,14.340480,-0.059215")
(COMMAND "POINT" "13.110250,14.415568,-0.057617")
(COMMAND "POINT" "13.186154,14.492174,-0.055059")
(COMMAND "POINT" "13.261019,14.570298,-0.051539")
(COMMAND "POINT" "13.334845,14.649940,-0.047059")
(COMMAND "POINT" "13.407630,14.731099,-0.041618")
(COMMAND "POINT" "13.479376,14.813777,-0.035216")
(COMMAND "POINT" "13.550083,14.897972,-0.027853")
(COMMAND "POINT" "13.619749,14.983686,-0.019529")
(COMMAND "POINT" "13.688376,15.070917,-0.010245")
(COMMAND "POINT" "13.755964,15.159666,0.000000")
(COMMAND "POINT" "4.275288,13.960498,0.831404")
(COMMAND "POINT" "4.350167,13.902635,0.863845")
(COMMAND "POINT" "4.425998,13.846196,0.894827")
(COMMAND "POINT" "4.502781,13.791181,0.924350")
(COMMAND "POINT" "4.580516,13.737590,0.952414")
(COMMAND "POINT" "4.659202,13.685423,0.979018")
(COMMAND "POINT" "4.738841,13.634680,1.004162")
(COMMAND "POINT" "4.819431,13.585361,1.027847")
(COMMAND "POINT" "4.900973,13.537466,1.050073")
(COMMAND "POINT" "4.983467,13.490995,1.070839")
(COMMAND "POINT" "5.066913,13.445948,1.090146")
(COMMAND "POINT" "5.151311,13.402325,1.107994")
(COMMAND "POINT" "5.236661,13.360127,1.124382")
(COMMAND "POINT" "5.322962,13.319352,1.139310")
(COMMAND "POINT" "5.410215,13.280001,1.152779")
(COMMAND "POINT" "5.498420,13.242074,1.164789")
(COMMAND "POINT" "5.587577,13.205571,1.175340")
(COMMAND "POINT" "5.677686,13.170493,1.184430")
(COMMAND "POINT" "5.768747,13.136838,1.192062")
(COMMAND "POINT" "5.860760,13.104607,1.198234")
(COMMAND "POINT" "5.953724,13.073801,1.202947")
(COMMAND "POINT" "6.047640,13.044418,1.206200")
(COMMAND "POINT" "6.142508,13.016459,1.207994")
(COMMAND "POINT" "6.238328,12.989925,1.208328")
(COMMAND "POINT" "6.335100,12.964814,1.207203")
(COMMAND "POINT" "6.432824,12.941128,1.204619")
(COMMAND "POINT" "6.531500,12.918865,1.200575")
(COMMAND "POINT" "6.631127,12.898027,1.195071")
(COMMAND "POINT" "6.731706,12.878612,1.188109")
(COMMAND "POINT" "6.833237,12.860622,1.179686")
(COMMAND "POINT" "6.935720,12.844055,1.169805")
(COMMAND "POINT" "7.039155,12.828913,1.158464")
(COMMAND "POINT" "7.143542,12.815195,1.145663")
(COMMAND "POINT" "7.248880,12.802900,1.131404")
(COMMAND "POINT" "7.355171,12.792030,1.115684")
(COMMAND "POINT" "7.462413,12.782584,1.098506")
(COMMAND "POINT" "7.570607,12.774561,1.079867")
(COMMAND "POINT" "7.679753,12.767963,1.059770")
(COMMAND "POINT" "7.789851,12.762789,1.038213")
(COMMAND "POINT" "7.900900,12.759039,1.015197")
(COMMAND "POINT" "8.012902,12.756712,0.990721")
(COMMAND "POINT" "8.125855,12.755810,0.964786")
(COMMAND "POINT" "8.239760,12.756332,0.937391")
(COMMAND "POINT" "8.354617,12.758278,0.908537")
(COMMAND "POINT" "8.470426,12.761648,0.878223")
(COMMAND "POINT" "8.587187,12.766442,0.846450")
(COMMAND "POINT" "8.704900,12.772660,0.813218")
(COMMAND "POINT" "8.823564,12.780301,0.778526")
(COMMAND "POINT" "8.943180,12.789367,0.742375")
(COMMAND "POINT" "9.063748,12.799857,0.704764")
(COMMAND "POINT" "9.185020,12.811787,0.666004")
(COMMAND "POINT" "9.305500,12.825247,0.627953")
(COMMAND "POINT" "9.424940,12.840253,0.590922")
(COMMAND "POINT" "9.543341,12.856805,0.554909")
(COMMAND "POINT" "9.660702,12.874904,0.519915")
(COMMAND "POINT" "9.777023,12.894548,0.485941")
(COMMAND "POINT" "9.892304,12.915738,0.452986")
(COMMAND "POINT" "10.006546,12.938475,0.421049")
(COMMAND "POINT" "10.119748,12.962758,0.390132")
(COMMAND "POINT" "10.231910,12.988586,0.360235")
(COMMAND "POINT" "10.343032,13.015961,0.331356")
(COMMAND "POINT" "10.453115,13.044882,0.303496")
(COMMAND "POINT" "10.562157,13.075349,0.276656")
(COMMAND "POINT" "10.670160,13.107362,0.250834")
(COMMAND "POINT" "10.777123,13.140921,0.226032")
(COMMAND "POINT" "10.883047,13.176026,0.202249")
(COMMAND "POINT" "10.987931,13.212677,0.179485")
(COMMAND "POINT" "11.091774,13.250875,0.157740")
(COMMAND "POINT" "11.194578,13.290618,0.137014")
(COMMAND "POINT" "11.296343,13.331908,0.117307")
(COMMAND "POINT" "11.397067,13.374743,0.098620")
(COMMAND "POINT" "11.496752,13.419125,0.080951")
(COMMAND "POINT" "11.595397,13.465053,0.064302")
(COMMAND "POINT" "11.693002,13.512526,0.048672")
(COMMAND "POINT" "11.789568,13.561546,0.034061")
(COMMAND "POINT" "11.885093,13.612112,0.020469")
(COMMAND "POINT" "11.979579,13.664224,0.007896")
(COMMAND "POINT" "12.073025,13.717882,-0.003658")
(COMMAND "POINT" "12.165432,13.773087,-0.014192")
(COMMAND "POINT" "12.256798,13.829837,-0.023708")
(COMMAND "POINT" "12.347125,13.888133,-0.032204")
(COMMAND "POINT" "12.436412,13.947976,-0.039681")
(COMMAND "POINT" "12.524659,14.009364,-0.046139")
(COMMAND "POINT" "12.611867,14.072299,-0.051578")
(COMMAND "POINT" "12.698035,14.136779,-0.055998")
(COMMAND "POINT" "12.783162,14.202806,-0.059399")
(COMMAND "POINT" "12.867251,14.270379,-0.061780")
(COMMAND "POINT" "12.950299,14.339498,-0.063143")
(COMMAND "POINT" "13.032308,14.410163,-0.063486")
(COMMAND "POINT" "13.113276,14.482374,-0.062810")
(COMMAND "POINT" "13.193206,14.556131,-0.061115")
(COMMAND "POINT" "13.272095,14.631434,-0.058401")
(COMMAND "POINT" "13.349944,14.708283,-0.054668")
(COMMAND "POINT" "13.426754,14.786679,-0.049916")
(COMMAND "POINT" "13.502524,14.866620,-0.044144")
(COMMAND "POINT" "13.577254,14.948107,-0.037354")
(COMMAND "POINT" "13.650945,15.031141,-0.029544")
(COMMAND "POINT" "13.723595,15.115721,-0.020715")
(COMMAND "POINT" "13.795206,15.201846,-0.010867")
(COMMAND "POINT" "13.865777,15.289518,0.000000")
(COMMAND "POINT" "4.191567,14.044226,0.879742")
(COMMAND "POINT" "4.265225,13.994063,0.914070")
(COMMAND "POINT" "4.339920,13.945115,0.946853")
(COMMAND "POINT" "4.415651,13.897382,0.978093")
(COMMAND "POINT" "4.492420,13.850864,1.007788")
(COMMAND "POINT" "4.570225,13.805561,1.035938")
(COMMAND "POINT" "4.649068,13.761474,1.062545")
(COMMAND "POINT" "4.728948,13.718601,1.087607")
(COMMAND "POINT" "4.809864,13.676944,1.111125")
(COMMAND "POINT" "4.891818,13.636501,1.133099")
(COMMAND "POINT" "4.974809,13.597274,1.153528")
(COMMAND "POINT" "5.058836,13.559262,1.172413")
(COMMAND "POINT" "5.143901,13.522464,1.189754")
(COMMAND "POINT" "5.230003,13.486882,1.205550")
(COMMAND "POINT" "5.317141,13.452515,1.219803")
(COMMAND "POINT" "5.405317,13.419363,1.232511")
(COMMAND "POINT" "5.494530,13.387426,1.243674")
(COMMAND "POINT" "5.584779,13.356704,1.253294")
(COMMAND "POINT" "5.676066,13.327197,1.261369")
(COMMAND "POINT" "5.768390,13.298905,1.267900")
(COMMAND "POINT" "5.861751,13.271829,1.272887")
(COMMAND "POINT" "5.956148,13.245967,1.276329")
(COMMAND "POINT" "6.051583,13.221321,1.278227")
(COMMAND "POINT" "6.148055,13.197889,1.278581")
(COMMAND "POINT" "6.245564,13.175673,1.277390")
(COMMAND "POINT" "6.344109,13.154671,1.274656")
(COMMAND "POINT" "6.443692,13.134885,1.270377")
(COMMAND "POINT" "6.544312,13.116314,1.264553")
(COMMAND "POINT" "6.645969,13.098957,1.257186")
(COMMAND "POINT" "6.748663,13.082816,1.248274")
(COMMAND "POINT" "6.852393,13.067890,1.237818")
(COMMAND "POINT" "6.957161,13.054179,1.225818")
(COMMAND "POINT" "7.062966,13.041683,1.212273")
(COMMAND "POINT" "7.169808,13.030403,1.197184")
(COMMAND "POINT" "7.277687,13.020337,1.180551")
(COMMAND "POINT" "7.386603,13.011486,1.162373")
(COMMAND "POINT" "7.496555,13.003850,1.142652")
(COMMAND "POINT" "7.607545,12.997430,1.121386")
(COMMAND "POINT" "7.719572,12.992224,1.098575")
(COMMAND "POINT" "7.832636,12.988234,1.074221")
(COMMAND "POINT" "7.946737,12.985458,1.048322")
(COMMAND "POINT" "8.061875,12.983898,1.020879")
(COMMAND "POINT" "8.178050,12.983553,0.991891")
(COMMAND "POINT" "8.295262,12.984423,0.961360")
(COMMAND "POINT" "8.413511,12.986508,0.929284")
(COMMAND "POINT" "8.532797,12.989807,0.895663")
(COMMAND "POINT" "8.653120,12.994323,0.860499")
(COMMAND "POINT" "8.774479,13.000053,0.823790")
(COMMAND "POINT" "8.896876,13.006998,0.785537")
(COMMAND "POINT" "9.020310,13.015158,0.745740")
(COMMAND "POINT" "9.144521,13.024578,0.704726")
(COMMAND "POINT" "9.267950,13.035527,0.664463")
(COMMAND "POINT" "9.390335,13.048050,0.625278")
(COMMAND "POINT" "9.511678,13.062146,0.587172")
(COMMAND "POINT" "9.631978,13.077816,0.550144")
(COMMAND "POINT" "9.751235,13.095060,0.514194")
(COMMAND "POINT" "9.869449,13.113877,0.479322")
(COMMAND "POINT" "9.986621,13.134269,0.445530")
(COMMAND "POINT" "10.102750,13.156233,0.412815")
(COMMAND "POINT" "10.217836,13.179772,0.381179")
(COMMAND "POINT" "10.331879,13.204884,0.350621")
(COMMAND "POINT" "10.444879,13.231570,0.321141")
(COMMAND "POINT" "10.556837,13.259830,0.292740")
(COMMAND "POINT" "10.667752,13.289663,0.265418")
(COMMAND "POINT" "10.777624,13.321070,0.239173")
(COMMAND "POINT" "10.886454,13.354051,0.214007")
(COMMAND "POINT" "10.994241,13.388605,0.189920")
(COMMAND "POINT" "11.100984,13.424734,0.166911")
(COMMAND "POINT" "11.206686,13.462435,0.144980")
(COMMAND "POINT" "11.311344,13.501711,0.124128")
(COMMAND "POINT" "11.414960,13.542560,0.104353")
(COMMAND "POINT" "11.517532,13.584983,0.085658")
(COMMAND "POINT" "11.619062,13.628980,0.068040")
(COMMAND "POINT" "11.719550,13.674550,0.051502")
(COMMAND "POINT" "11.818994,13.721694,0.036041")
(COMMAND "POINT" "11.917396,13.770412,0.021659")
(COMMAND "POINT" "12.014755,13.820703,0.008355")
(COMMAND "POINT" "12.111071,13.872568,-0.003870")
(COMMAND "POINT" "12.206345,13.926007,-0.015017")
(COMMAND "POINT" "12.300575,13.981020,-0.025086")
(COMMAND "POINT" "12.393763,14.037606,-0.034076")
(COMMAND "POINT" "12.485908,14.095766,-0.041988")
(COMMAND "POINT" "12.577011,14.155500,-0.048822")
(COMMAND "POINT" "12.667070,14.216807,-0.054577")
(COMMAND "POINT" "12.756087,14.279688,-0.059254")
(COMMAND "POINT" "12.844061,14.344143,-0.062852")
(COMMAND "POINT" "12.930992,14.410171,-0.065372")
(COMMAND "POINT" "13.016881,14.477773,-0.066814")
(COMMAND "POINT" "13.101727,14.546949,-0.067177")
(COMMAND "POINT" "13.185530,14.617698,-0.066462")
(COMMAND "POINT" "13.268290,14.690022,-0.064668")
(COMMAND "POINT" "13.350007,14.763918,-0.061797")
(COMMAND "POINT" "13.430682,14.839389,-0.057846")
(COMMAND "POINT" "13.510314,14.916433,-0.052818")
(COMMAND "POINT" "13.588903,14.995051,-0.046711")
(COMMAND "POINT" "13.666449,15.075243,-0.039525")
(COMMAND "POINT" "13.742953,15.157008,-0.031262")
(COMMAND "POINT" "13.818414,15.240347,-0.021919")
(COMMAND "POINT" "13.892832,15.325260,-0.011499")
(COMMAND "POINT" "13.966207,15.411747,0.000000")
(COMMAND "POINT" "4.109249,14.127254,0.928834")
(COMMAND "POINT" "4.181508,14.084781,0.965077")
(COMMAND "POINT" "4.254892,14.043312,0.999690")
(COMMAND "POINT" "4.329401,14.002849,1.032673")
(COMMAND "POINT" "4.405035,13.963390,1.064025")
(COMMAND "POINT" "4.481793,13.924936,1.093747")
(COMMAND "POINT" "4.559677,13.887486,1.121838")
(COMMAND "POINT" "4.638686,13.851041,1.148299")
(COMMAND "POINT" "4.718820,13.815601,1.173129")
(COMMAND "POINT" "4.800079,13.781165,1.196329")
(COMMAND "POINT" "4.882463,13.747734,1.217898")
(COMMAND "POINT" "4.965971,13.715308,1.237837")
(COMMAND "POINT" "5.050605,13.683886,1.256146")
(COMMAND "POINT" "5.136364,13.653469,1.272824")
(COMMAND "POINT" "5.223248,13.624056,1.287871")
(COMMAND "POINT" "5.311257,13.595649,1.301288")
(COMMAND "POINT" "5.400390,13.568246,1.313075")
(COMMAND "POINT" "5.490649,13.541847,1.323231")
(COMMAND "POINT" "5.582033,13.516454,1.331757")
(COMMAND "POINT" "5.674542,13.492065,1.338653")
(COMMAND "POINT" "5.768176,13.468680,1.343917")
(COMMAND "POINT" "5.862935,13.446300,1.347552")
(COMMAND "POINT" "5.958818,13.424925,1.349556")
(COMMAND "POINT" "6.055827,13.404555,1.349929")
(COMMAND "POINT" "6.153961,13.385189,1.348673")
(COMMAND "POINT" "6.253220,13.366828,1.345785")
(COMMAND "POINT" "6.353604,13.349472,1.341267")
(COMMAND "POINT" "6.455112,13.333120,1.335119")
(COMMAND "POINT" "6.557746,13.317773,1.327340")
(COMMAND "POINT" "6.661505,13.303430,1.317931")
(COMMAND "POINT" "6.766389,13.290093,1.306892")
(COMMAND "POINT" "6.872398,13.277760,1.294222")
(COMMAND "POINT" "6.979531,13.266431,1.279921")
(COMMAND "POINT" "7.087790,13.256107,1.263990")
(COMMAND "POINT" "7.197174,13.246788,1.246429")
(COMMAND "POINT" "7.307683,13.238474,1.227237")
(COMMAND "POINT" "7.419317,13.231164,1.206415")
(COMMAND "POINT" "7.532076,13.224859,1.183962")
(COMMAND "POINT" "7.645959,13.219558,1.159879")
(COMMAND "POINT" "7.760968,13.215262,1.134165")
(COMMAND "POINT" "7.877102,13.211971,1.106821")
(COMMAND "POINT" "7.994361,13.209685,1.077847")
(COMMAND "POINT" "8.112745,13.208403,1.047242")
(COMMAND "POINT" "8.232254,13.208126,1.015006")
(COMMAND "POINT" "8.352887,13.208853,0.981140")
(COMMAND "POINT" "8.474646,13.210585,0.945644")
(COMMAND "POINT" "8.597530,13.213322,0.908517")
(COMMAND "POINT" "8.721539,13.217063,0.869760")
(COMMAND "POINT" "8.846673,13.221810,0.829372")
(COMMAND "POINT" "8.972931,13.227560,0.787354")
(COMMAND "POINT" "9.100044,13.234390,0.744052")
(COMMAND "POINT" "9.226379,13.242747,0.701542")
(COMMAND "POINT" "9.351665,13.252704,0.660170")
(COMMAND "POINT" "9.475903,13.264261,0.619937")
(COMMAND "POINT" "9.599092,13.277420,0.580843")
(COMMAND "POINT" "9.721233,13.292179,0.542887")
(COMMAND "POINT" "9.842325,13.308539,0.506070")
(COMMAND "POINT" "9.962368,13.326500,0.470391")
(COMMAND "POINT" "10.081363,13.346062,0.435851")
(COMMAND "POINT" "10.199309,13.367224,0.402450")
(COMMAND "POINT" "10.316206,13.389987,0.370187")
(COMMAND "POINT" "10.432055,13.414351,0.339062")
(COMMAND "POINT" "10.546855,13.440316,0.309076")
(COMMAND "POINT" "10.660606,13.467881,0.280229")
(COMMAND "POINT" "10.773309,13.497047,0.252520")
(COMMAND "POINT" "10.884963,13.527814,0.225950")
(COMMAND "POINT" "10.995568,13.560182,0.200518")
(COMMAND "POINT" "11.105125,13.594151,0.176225")
(COMMAND "POINT" "11.213633,13.629720,0.153070")
(COMMAND "POINT" "11.321092,13.666890,0.131054")
(COMMAND "POINT" "11.427503,13.705661,0.110177")
(COMMAND "POINT" "11.532865,13.746033,0.090438")
(COMMAND "POINT" "11.637179,13.788005,0.071837")
(COMMAND "POINT" "11.740444,13.831578,0.054376")
(COMMAND "POINT" "11.842660,13.876752,0.038052")
(COMMAND "POINT" "11.943828,13.923527,0.022867")
(COMMAND "POINT" "12.043946,13.971903,0.008821")
(COMMAND "POINT" "12.143017,14.021879,-0.004086")
(COMMAND "POINT" "12.241038,14.073456,-0.015855")
(COMMAND "POINT" "12.338011,14.126634,-0.026486")
(COMMAND "POINT" "12.433935,14.181412,-0.035978")
(COMMAND "POINT" "12.528811,14.237792,-0.044331")
(COMMAND "POINT" "12.622638,14.295772,-0.051546")
(COMMAND "POINT" "12.715416,14.355353,-0.057622")
(COMMAND "POINT" "12.807146,14.416534,-0.062560")
(COMMAND "POINT" "12.897827,14.479317,-0.066359")
(COMMAND "POINT" "12.987460,14.543700,-0.069020")
(COMMAND "POINT" "13.076043,14.609684,-0.070542")
(COMMAND "POINT" "13.163578,14.677269,-0.070926")
(COMMAND "POINT" "13.250065,14.746454,-0.070171")
(COMMAND "POINT" "13.335503,14.817240,-0.068277")
(COMMAND "POINT" "13.419892,14.889628,-0.065245")
(COMMAND "POINT" "13.503232,14.963615,-0.061074")
(COMMAND "POINT" "13.585524,15.039204,-0.055765")
(COMMAND "POINT" "13.666767,15.116393,-0.049317")
(COMMAND "POINT" "13.746962,15.195184,-0.041731")
(COMMAND "POINT" "13.826108,15.275574,-0.033006")
(COMMAND "POINT" "13.904205,15.357566,-0.023143")
(COMMAND "POINT" "13.981253,15.441159,-0.012141")
(COMMAND "POINT" "14.057253,15.526352,0.000000")
(COMMAND "POINT" "4.028333,14.209582,0.978680")
(COMMAND "POINT" "4.099016,14.174789,1.016868")
(COMMAND "POINT" "4.170915,14.140789,1.053339")
(COMMAND "POINT" "4.244030,14.107581,1.088091")
(COMMAND "POINT" "4.318360,14.075167,1.121126")
(COMMAND "POINT" "4.393906,14.043545,1.152443")
(COMMAND "POINT" "4.470668,14.012716,1.182041")
(COMMAND "POINT" "4.548646,13.982680,1.209922")
(COMMAND "POINT" "4.627840,13.953437,1.236085")
(COMMAND "POINT" "4.708250,13.924986,1.260530")
(COMMAND "POINT" "4.789875,13.897328,1.283257")
(COMMAND "POINT" "4.872716,13.870463,1.304266")
(COMMAND "POINT" "4.956773,13.844391,1.323557")
(COMMAND "POINT" "5.042046,13.819112,1.341130")
(COMMAND "POINT" "5.128535,13.794625,1.356985")
(COMMAND "POINT" "5.216239,13.770932,1.371122")
(COMMAND "POINT" "5.305160,13.748031,1.383541")
(COMMAND "POINT" "5.395296,13.725923,1.394243")
(COMMAND "POINT" "5.486648,13.704607,1.403226")
(COMMAND "POINT" "5.579216,13.684085,1.410491")
(COMMAND "POINT" "5.672999,13.664355,1.416039")
(COMMAND "POINT" "5.767999,13.645418,1.419868")
(COMMAND "POINT" "5.864214,13.627274,1.421980")
(COMMAND "POINT" "5.961645,13.609923,1.422374")
(COMMAND "POINT" "6.060292,13.593364,1.421049")
(COMMAND "POINT" "6.160155,13.577599,1.418007")
(COMMAND "POINT" "6.261234,13.562626,1.413247")
(COMMAND "POINT" "6.363528,13.548446,1.406768")
(COMMAND "POINT" "6.467039,13.535059,1.398572")
(COMMAND "POINT" "6.571765,13.522464,1.388658")
(COMMAND "POINT" "6.677707,13.510662,1.377026")
(COMMAND "POINT" "6.784865,13.499654,1.363676")
(COMMAND "POINT" "6.893238,13.489438,1.348608")
(COMMAND "POINT" "7.002828,13.480014,1.331822")
(COMMAND "POINT" "7.113633,13.471384,1.313319")
(COMMAND "POINT" "7.225654,13.463546,1.293097")
(COMMAND "POINT" "7.338891,13.456502,1.271157")
(COMMAND "POINT" "7.453344,13.450250,1.247500")
(COMMAND "POINT" "7.569012,13.444790,1.222124")
(COMMAND "POINT" "7.685897,13.440124,1.195030")
(COMMAND "POINT" "7.803997,13.436250,1.166219")
(COMMAND "POINT" "7.923313,13.433170,1.135689")
(COMMAND "POINT" "8.043845,13.430882,1.103442")
(COMMAND "POINT" "8.165593,13.429387,1.069477")
(COMMAND "POINT" "8.288556,13.428684,1.033793")
(COMMAND "POINT" "8.412736,13.428775,0.996392")
(COMMAND "POINT" "8.538131,13.429658,0.957273")
(COMMAND "POINT" "8.664742,13.431334,0.916436")
(COMMAND "POINT" "8.792569,13.433803,0.873881")
(COMMAND "POINT" "8.921611,13.437065,0.829608")
(COMMAND "POINT" "9.051586,13.441223,0.783981")
(COMMAND "POINT" "9.180787,13.446905,0.739190")
(COMMAND "POINT" "9.308931,13.454214,0.695598")
(COMMAND "POINT" "9.436017,13.463151,0.653206")
(COMMAND "POINT" "9.562046,13.473714,0.612014")
(COMMAND "POINT" "9.687017,13.485905,0.572021")
(COMMAND "POINT" "9.810931,13.499724,0.533228")
(COMMAND "POINT" "9.933788,13.515169,0.495635")
(COMMAND "POINT" "10.055587,13.532242,0.459241")
(COMMAND "POINT" "10.176329,13.550942,0.424047")
(COMMAND "POINT" "10.296013,13.571270,0.390053")
(COMMAND "POINT" "10.414640,13.593225,0.357258")
(COMMAND "POINT" "10.532210,13.616807,0.325663")
(COMMAND "POINT" "10.648722,13.642016,0.295267")
(COMMAND "POINT" "10.764176,13.668853,0.266071")
(COMMAND "POINT" "10.878574,13.697317,0.238075")
(COMMAND "POINT" "10.991913,13.727408,0.211279")
(COMMAND "POINT" "11.104196,13.759126,0.185682")
(COMMAND "POINT" "11.215421,13.792472,0.161285")
(COMMAND "POINT" "11.325588,13.827445,0.138087")
(COMMAND "POINT" "11.434699,13.864046,0.116089")
(COMMAND "POINT" "11.542751,13.902274,0.095291")
(COMMAND "POINT" "11.649747,13.942129,0.075693")
(COMMAND "POINT" "11.755685,13.983611,0.057294")
(COMMAND "POINT" "11.860565,14.026721,0.040094")
(COMMAND "POINT" "11.964388,14.071458,0.024095")
(COMMAND "POINT" "12.067154,14.117822,0.009295")
(COMMAND "POINT" "12.168862,14.165813,-0.004306")
(COMMAND "POINT" "12.269513,14.215432,-0.016706")
(COMMAND "POINT" "12.369106,14.266678,-0.027907")
(COMMAND "POINT" "12.467642,14.319552,-0.037909")
(COMMAND "POINT" "12.565121,14.374053,-0.046710")
(COMMAND "POINT" "12.661542,14.430181,-0.054312")
(COMMAND "POINT" "12.756906,14.487936,-0.060715")
(COMMAND "POINT" "12.851212,14.547319,-0.065917")
(COMMAND "POINT" "12.944461,14.608328,-0.069921")
(COMMAND "POINT" "13.036652,14.670966,-0.072724")
(COMMAND "POINT" "13.127786,14.735230,-0.074328")
(COMMAND "POINT" "13.217863,14.801122,-0.074732")
(COMMAND "POINT" "13.306882,14.868641,-0.073936")
(COMMAND "POINT" "13.394844,14.937788,-0.071941")
(COMMAND "POINT" "13.481748,15.008561,-0.068746")
(COMMAND "POINT" "13.567595,15.080962,-0.064352")
(COMMAND "POINT" "13.652385,15.154991,-0.058758")
(COMMAND "POINT" "13.736117,15.230646,-0.051964")
(COMMAND "POINT" "13.818792,15.307929,-0.043970")
(COMMAND "POINT" "13.900409,15.386839,-0.034777")
(COMMAND "POINT" "13.980969,15.467377,-0.024385")
(COMMAND "POINT" "14.060471,15.549542,-0.012792")
(COMMAND "POINT" "14.138916,15.633334,0.000000")
(COMMAND "POINT" "3.948820,14.291211,1.029280")
(COMMAND "POINT" "4.017750,14.264088,1.069443")
(COMMAND "POINT" "4.087989,14.237544,1.107799")
(COMMAND "POINT" "4.159538,14.211580,1.144348")
(COMMAND "POINT" "4.232396,14.186195,1.179091")
(COMMAND "POINT" "4.306564,14.161390,1.212026")
(COMMAND "POINT" "4.382042,14.137165,1.243155")
(COMMAND "POINT" "4.458828,14.113518,1.272478")
(COMMAND "POINT" "4.536925,14.090452,1.299993")
(COMMAND "POINT" "4.616331,14.067965,1.325702")
(COMMAND "POINT" "4.697046,14.046057,1.349604")
(COMMAND "POINT" "4.779071,14.024729,1.371699")
(COMMAND "POINT" "4.862405,14.003980,1.391987")
(COMMAND "POINT" "4.947049,13.983811,1.410469")
(COMMAND "POINT" "5.033002,13.964221,1.427144")
(COMMAND "POINT" "5.120265,13.945211,1.442012")
(COMMAND "POINT" "5.208838,13.926781,1.455073")
(COMMAND "POINT" "5.298719,13.908930,1.466328")
(COMMAND "POINT" "5.389911,13.891658,1.475776")
(COMMAND "POINT" "5.482412,13.874966,1.483417")
(COMMAND "POINT" "5.576222,13.858853,1.489251")
(COMMAND "POINT" "5.671342,13.843320,1.493279")
(COMMAND "POINT" "5.767771,13.828367,1.495499")
(COMMAND "POINT" "5.865510,13.813992,1.495913")
(COMMAND "POINT" "5.964558,13.800198,1.494520")
(COMMAND "POINT" "6.064916,13.786983,1.491321")
(COMMAND "POINT" "6.166583,13.774347,1.486314")
(COMMAND "POINT" "6.269560,13.762291,1.479501")
(COMMAND "POINT" "6.373846,13.750814,1.470881")
(COMMAND "POINT" "6.479442,13.739917,1.460455")
(COMMAND "POINT" "6.586347,13.729600,1.448221")
(COMMAND "POINT" "6.694562,13.719862,1.434181")
(COMMAND "POINT" "6.804086,13.710703,1.418334")
(COMMAND "POINT" "6.914920,13.702124,1.400680")
(COMMAND "POINT" "7.027063,13.694124,1.381220")
(COMMAND "POINT" "7.140516,13.686704,1.359953")
(COMMAND "POINT" "7.255278,13.679864,1.336879")
(COMMAND "POINT" "7.371350,13.673603,1.311998")
(COMMAND "POINT" "7.488731,13.667921,1.285310")
(COMMAND "POINT" "7.607422,13.662819,1.256816")
(COMMAND "POINT" "7.727422,13.658296,1.226515")
(COMMAND "POINT" "7.848731,13.654353,1.194407")
(COMMAND "POINT" "7.971351,13.650990,1.160492")
(COMMAND "POINT" "8.095279,13.648206,1.124771")
(COMMAND "POINT" "8.220517,13.646001,1.087243")
(COMMAND "POINT" "8.347065,13.644376,1.047908")
(COMMAND "POINT" "8.474922,13.643331,1.006766")
(COMMAND "POINT" "8.604089,13.642864,0.963817")
(COMMAND "POINT" "8.734565,13.642978,0.919062")
(COMMAND "POINT" "8.866351,13.643671,0.872500")
(COMMAND "POINT" "8.999148,13.645078,0.824515")
(COMMAND "POINT" "9.131174,13.648003,0.777408")
(COMMAND "POINT" "9.262131,13.652582,0.731562")
(COMMAND "POINT" "9.392019,13.658815,0.686979")
(COMMAND "POINT" "9.520838,13.666700,0.643657")
(COMMAND "POINT" "9.648588,13.676239,0.601596")
(COMMAND "POINT" "9.775269,13.687431,0.560797")
(COMMAND "POINT" "9.900880,13.700276,0.521260")
(COMMAND "POINT" "10.025423,13.714775,0.482985")
(COMMAND "POINT" "10.148896,13.730927,0.445971")
(COMMAND "POINT" "10.271301,13.748732,0.410219")
(COMMAND "POINT" "10.392636,13.768191,0.375729")
(COMMAND "POINT" "10.512902,13.789303,0.342500")
(COMMAND "POINT" "10.632099,13.812068,0.310533")
(COMMAND "POINT" "10.750227,13.836486,0.279828")
(COMMAND "POINT" "10.867286,13.862558,0.250384")
(COMMAND "POINT" "10.983276,13.890282,0.222202")
(COMMAND "POINT" "11.098197,13.919661,0.195282")
(COMMAND "POINT" "11.212049,13.950692,0.169624")
(COMMAND "POINT" "11.324832,13.983377,0.145227")
(COMMAND "POINT" "11.436546,14.017715,0.122091")
(COMMAND "POINT" "11.547190,14.053706,0.100218")
(COMMAND "POINT" "11.656766,14.091351,0.079606")
(COMMAND "POINT" "11.765272,14.130648,0.060256")
(COMMAND "POINT" "11.872709,14.171599,0.042167")
(COMMAND "POINT" "11.979078,14.214204,0.025340")
(COMMAND "POINT" "12.084377,14.258461,0.009775")
(COMMAND "POINT" "12.188607,14.304372,-0.004528")
(COMMAND "POINT" "12.291768,14.351937,-0.017570")
(COMMAND "POINT" "12.393860,14.401154,-0.029350")
(COMMAND "POINT" "12.494883,14.452025,-0.039869")
(COMMAND "POINT" "12.594837,14.504549,-0.049125")
(COMMAND "POINT" "12.693722,14.558726,-0.057120")
(COMMAND "POINT" "12.791538,14.614557,-0.063854")
(COMMAND "POINT" "12.888284,14.672041,-0.069326")
(COMMAND "POINT" "12.983962,14.731178,-0.073536")
(COMMAND "POINT" "13.078570,14.791968,-0.076484")
(COMMAND "POINT" "13.172110,14.854412,-0.078171")
(COMMAND "POINT" "13.264580,14.918509,-0.078596")
(COMMAND "POINT" "13.355982,14.984259,-0.077759")
(COMMAND "POINT" "13.446314,15.051663,-0.075661")
(COMMAND "POINT" "13.535577,15.120720,-0.072301")
(COMMAND "POINT" "13.623771,15.191430,-0.067679")
(COMMAND "POINT" "13.710896,15.263793,-0.061796")
(COMMAND "POINT" "13.796952,15.337810,-0.054650")
(COMMAND "POINT" "13.881939,15.413480,-0.046244")
(COMMAND "POINT" "13.965857,15.490803,-0.036575")
(COMMAND "POINT" "14.048705,15.569779,-0.025645")
(COMMAND "POINT" "14.130485,15.650409,-0.013453")
(COMMAND "POINT" "14.211196,15.732692,0.000000")
(COMMAND "POINT" "3.870708,14.372140,1.080633")
(COMMAND "POINT" "3.937708,14.352677,1.122800")
(COMMAND "POINT" "4.006113,14.333578,1.163070")
(COMMAND "POINT" "4.075925,14.314844,1.201443")
(COMMAND "POINT" "4.147143,14.296475,1.237919")
(COMMAND "POINT" "4.219767,14.278471,1.272498")
(COMMAND "POINT" "4.293797,14.260831,1.305180")
(COMMAND "POINT" "4.369232,14.243556,1.335965")
(COMMAND "POINT" "4.446074,14.226646,1.364853")
(COMMAND "POINT" "4.524322,14.210101,1.391845")
(COMMAND "POINT" "4.603976,14.193920,1.416939")
(COMMAND "POINT" "4.685035,14.178104,1.440137")
(COMMAND "POINT" "4.767501,14.162653,1.461438")
(COMMAND "POINT" "4.851373,14.147567,1.480841")
(COMMAND "POINT" "4.936651,14.132845,1.498348")
(COMMAND "POINT" "5.023334,14.118488,1.513958")
(COMMAND "POINT" "5.111424,14.104496,1.527671")
(COMMAND "POINT" "5.200920,14.090869,1.539487")
(COMMAND "POINT" "5.291822,14.077606,1.549406")
(COMMAND "POINT" "5.384129,14.064708,1.557429")
(COMMAND "POINT" "5.477843,14.052175,1.563554")
(COMMAND "POINT" "5.572963,14.040006,1.567782")
(COMMAND "POINT" "5.669488,14.028203,1.570114")
(COMMAND "POINT" "5.767420,14.016764,1.570548")
(COMMAND "POINT" "5.866758,14.005690,1.569086")
(COMMAND "POINT" "5.967501,13.994980,1.565727")
(COMMAND "POINT" "6.069651,13.984636,1.560471")
(COMMAND "POINT" "6.173207,13.974656,1.553318")
(COMMAND "POINT" "6.278169,13.965041,1.544268")
(COMMAND "POINT" "6.384536,13.955790,1.533321")
(COMMAND "POINT" "6.492310,13.946904,1.520477")
(COMMAND "POINT" "6.601490,13.938384,1.505736")
(COMMAND "POINT" "6.712075,13.930227,1.489099")
(COMMAND "POINT" "6.824067,13.922436,1.470564")
(COMMAND "POINT" "6.937465,13.915009,1.450133")
(COMMAND "POINT" "7.052268,13.907947,1.427805")
(COMMAND "POINT" "7.168478,13.901250,1.403579")
(COMMAND "POINT" "7.286093,13.894918,1.377457")
(COMMAND "POINT" "7.405115,13.888950,1.349438")
(COMMAND "POINT" "7.525543,13.883347,1.319522")
(COMMAND "POINT" "7.647376,13.878109,1.287709")
(COMMAND "POINT" "7.770616,13.873236,1.253999")
(COMMAND "POINT" "7.895262,13.868727,1.218392")
(COMMAND "POINT" "8.021313,13.864583,1.180889")
(COMMAND "POINT" "8.148771,13.860804,1.141488")
(COMMAND "POINT" "8.277634,13.857389,1.100191")
(COMMAND "POINT" "8.407904,13.854340,1.056996")
(COMMAND "POINT" "8.539580,13.851655,1.011905")
(COMMAND "POINT" "8.672661,13.849334,0.964917")
(COMMAND "POINT" "8.807149,13.847379,0.916032")
(COMMAND "POINT" "8.942731,13.845952,0.865652")
(COMMAND "POINT" "9.077541,13.846040,0.816195")
(COMMAND "POINT" "9.211267,13.847807,0.768062")
(COMMAND "POINT" "9.343910,13.851253,0.721254")
(COMMAND "POINT" "9.475469,13.856377,0.675770")
(COMMAND "POINT" "9.605945,13.863180,0.631611")
(COMMAND "POINT" "9.735337,13.871661,0.588777")
(COMMAND "POINT" "9.863645,13.881821,0.547267")
(COMMAND "POINT" "9.990870,13.893660,0.507082")
(COMMAND "POINT" "10.117011,13.907178,0.468222")
(COMMAND "POINT" "10.242068,13.922374,0.430686")
(COMMAND "POINT" "10.366042,13.939250,0.394475")
(COMMAND "POINT" "10.488932,13.957803,0.359589")
(COMMAND "POINT" "10.610739,13.978036,0.326027")
(COMMAND "POINT" "10.731462,13.999947,0.293789")
(COMMAND "POINT" "10.851101,14.023537,0.262877")
(COMMAND "POINT" "10.969657,14.048806,0.233289")
(COMMAND "POINT" "11.087129,14.075753,0.205025")
(COMMAND "POINT" "11.203518,14.104379,0.178087")
(COMMAND "POINT" "11.318823,14.134684,0.152472")
(COMMAND "POINT" "11.433044,14.166667,0.128183")
(COMMAND "POINT" "11.546182,14.200330,0.105218")
(COMMAND "POINT" "11.658236,14.235671,0.083578")
(COMMAND "POINT" "11.769206,14.272690,0.063262")
(COMMAND "POINT" "11.879093,14.311388,0.044271")
(COMMAND "POINT" "11.987896,14.351765,0.026605")
(COMMAND "POINT" "12.095616,14.393821,0.010263")
(COMMAND "POINT" "12.202252,14.437556,-0.004754")
(COMMAND "POINT" "12.307805,14.482969,-0.018447")
(COMMAND "POINT" "12.412273,14.530061,-0.030814")
(COMMAND "POINT" "12.515659,14.578831,-0.041858")
(COMMAND "POINT" "12.617960,14.629281,-0.051576")
(COMMAND "POINT" "12.719178,14.681409,-0.059970")
(COMMAND "POINT" "12.819313,14.735215,-0.067040")
(COMMAND "POINT" "12.918363,14.790701,-0.072784")
(COMMAND "POINT" "13.016331,14.847865,-0.077204")
(COMMAND "POINT" "13.113214,14.906708,-0.080300")
(COMMAND "POINT" "13.209014,14.967229,-0.082071")
(COMMAND "POINT" "13.303730,15.029430,-0.082517")
(COMMAND "POINT" "13.397363,15.093308,-0.081639")
(COMMAND "POINT" "13.489912,15.158866,-0.079436")
(COMMAND "POINT" "13.581378,15.226103,-0.075908")
(COMMAND "POINT" "13.671759,15.295018,-0.071056")
(COMMAND "POINT" "13.761058,15.365611,-0.064879")
(COMMAND "POINT" "13.849272,15.437884,-0.057377")
(COMMAND "POINT" "13.936403,15.511835,-0.048551")
(COMMAND "POINT" "14.022451,15.587465,-0.038400")
(COMMAND "POINT" "14.107415,15.664774,-0.026925")
(COMMAND "POINT" "14.191295,15.743761,-0.014125")
(COMMAND "POINT" "14.274091,15.824427,0.000000")
(COMMAND "POINT" "3.793998,14.452370,1.132741")
(COMMAND "POINT" "3.858891,14.440556,1.176941")
(COMMAND "POINT" "3.925289,14.428891,1.219152")
(COMMAND "POINT" "3.993192,14.417374,1.259376")
(COMMAND "POINT" "4.062600,14.406006,1.297610")
(COMMAND "POINT" "4.133514,14.394787,1.333857")
(COMMAND "POINT" "4.205934,14.383716,1.368115")
(COMMAND "POINT" "4.279858,14.372793,1.400385")
(COMMAND "POINT" "4.355288,14.362020,1.430666")
(COMMAND "POINT" "4.432223,14.351394,1.458959")
(COMMAND "POINT" "4.510664,14.340917,1.485263")
(COMMAND "POINT" "4.590610,14.330589,1.509579")
(COMMAND "POINT" "4.672061,14.320410,1.531907")
(COMMAND "POINT" "4.755017,14.310378,1.552247")
(COMMAND "POINT" "4.839479,14.300496,1.570598")
(COMMAND "POINT" "4.925447,14.290762,1.586960")
(COMMAND "POINT" "5.012919,14.281176,1.601334")
(COMMAND "POINT" "5.101897,14.271739,1.613720")
(COMMAND "POINT" "5.192380,14.262451,1.624118")
(COMMAND "POINT" "5.284369,14.253311,1.632527")
(COMMAND "POINT" "5.377863,14.244320,1.638947")
(COMMAND "POINT" "5.472862,14.235477,1.643380")
(COMMAND "POINT" "5.569367,14.226783,1.645824")
(COMMAND "POINT" "5.667376,14.218237,1.646279")
(COMMAND "POINT" "5.766892,14.209840,1.644747")
(COMMAND "POINT" "5.867912,14.201591,1.641225")
(COMMAND "POINT" "5.970438,14.193491,1.635716")
(COMMAND "POINT" "6.074469,14.185540,1.628218")
(COMMAND "POINT" "6.180006,14.177737,1.618731")
(COMMAND "POINT" "6.287048,14.170083,1.607257")
(COMMAND "POINT" "6.395595,14.162577,1.593794")
(COMMAND "POINT" "6.505648,14.155219,1.578342")
(COMMAND "POINT" "6.617206,14.148011,1.560902")
(COMMAND "POINT" "6.730269,14.140950,1.541474")
(COMMAND "POINT" "6.844837,14.134039,1.520057")
(COMMAND "POINT" "6.960911,14.127276,1.496652")
(COMMAND "POINT" "7.078490,14.120661,1.471259")
(COMMAND "POINT" "7.197575,14.114195,1.443877")
(COMMAND "POINT" "7.318165,14.107877,1.414507")
(COMMAND "POINT" "7.440260,14.101708,1.383148")
(COMMAND "POINT" "7.563861,14.095688,1.349802")
(COMMAND "POINT" "7.688967,14.089816,1.314466")
(COMMAND "POINT" "7.815578,14.084093,1.277143")
(COMMAND "POINT" "7.943694,14.078518,1.237830")
(COMMAND "POINT" "8.073316,14.073092,1.196530")
(COMMAND "POINT" "8.204444,14.067814,1.153241")
(COMMAND "POINT" "8.337076,14.062685,1.107964")
(COMMAND "POINT" "8.471214,14.057704,1.060698")
(COMMAND "POINT" "8.606857,14.052872,1.011444")
(COMMAND "POINT" "8.744006,14.048189,0.960202")
(COMMAND "POINT" "8.882334,14.043848,0.907393")
(COMMAND "POINT" "9.019887,14.041017,0.855551")
(COMMAND "POINT" "9.156339,14.039889,0.805097")
(COMMAND "POINT" "9.291689,14.040465,0.756032")
(COMMAND "POINT" "9.425939,14.042744,0.708356")
(COMMAND "POINT" "9.559088,14.046727,0.662067")
(COMMAND "POINT" "9.691136,14.052414,0.617168")
(COMMAND "POINT" "9.822082,14.059804,0.573656")
(COMMAND "POINT" "9.951928,14.068898,0.531534")
(COMMAND "POINT" "10.080672,14.079695,0.490799")
(COMMAND "POINT" "10.208316,14.092196,0.451454")
(COMMAND "POINT" "10.334858,14.106401,0.413496")
(COMMAND "POINT" "10.460300,14.122309,0.376928")
(COMMAND "POINT" "10.584640,14.139921,0.341747")
(COMMAND "POINT" "10.707880,14.159236,0.307956")
(COMMAND "POINT" "10.830018,14.180255,0.275552")
(COMMAND "POINT" "10.951055,14.202978,0.244538")
(COMMAND "POINT" "11.070992,14.227404,0.214911")
(COMMAND "POINT" "11.189827,14.253534,0.186674")
(COMMAND "POINT" "11.307561,14.281367,0.159825")
(COMMAND "POINT" "11.424194,14.310904,0.134364")
(COMMAND "POINT" "11.539726,14.342145,0.110292")
(COMMAND "POINT" "11.654157,14.375089,0.087608")
(COMMAND "POINT" "11.767487,14.409736,0.066313")
(COMMAND "POINT" "11.879716,14.446088,0.046406")
(COMMAND "POINT" "11.990844,14.484143,0.027888")
(COMMAND "POINT" "12.100871,14.523901,0.010758")
(COMMAND "POINT" "12.209797,14.565363,-0.004983")
(COMMAND "POINT" "12.317622,14.608529,-0.019336")
(COMMAND "POINT" "12.424346,14.653398,-0.032300")
(COMMAND "POINT" "12.529968,14.699971,-0.043876")
(COMMAND "POINT" "12.634490,14.748248,-0.054063")
(COMMAND "POINT" "12.737911,14.798228,-0.062862")
(COMMAND "POINT" "12.840230,14.849911,-0.070272")
(COMMAND "POINT" "12.941449,14.903299,-0.076294")
(COMMAND "POINT" "13.041567,14.958389,-0.080927")
(COMMAND "POINT" "13.140583,15.015184,-0.084172")
(COMMAND "POINT" "13.238499,15.073682,-0.086028")
(COMMAND "POINT" "13.335313,15.133884,-0.086496")
(COMMAND "POINT" "13.431027,15.195789,-0.085575")
(COMMAND "POINT" "13.525639,15.259398,-0.083266")
(COMMAND "POINT" "13.619150,15.324710,-0.079568")
(COMMAND "POINT" "13.711561,15.391726,-0.074482")
(COMMAND "POINT" "13.802870,15.460446,-0.068007")
(COMMAND "POINT" "13.893078,15.530869,-0.060144")
(COMMAND "POINT" "13.982185,15.602996,-0.050892")
(COMMAND "POINT" "14.070191,15.676826,-0.040252")
(COMMAND "POINT" "14.157097,15.752360,-0.028223")
(COMMAND "POINT" "14.242901,15.829598,-0.014806")
(COMMAND "POINT" "14.327604,15.908539,0.000000")
(COMMAND "POINT" "3.718691,14.531900,1.185602")
(COMMAND "POINT" "3.781299,14.527726,1.231865")
(COMMAND "POINT" "3.845514,14.523482,1.276046")
(COMMAND "POINT" "3.911338,14.519170,1.318146")
(COMMAND "POINT" "3.978768,14.514789,1.358166")
(COMMAND "POINT" "4.047807,14.510338,1.396103")
(COMMAND "POINT" "4.118452,14.505819,1.431960")
(COMMAND "POINT" "4.190706,14.501230,1.465736")
(COMMAND "POINT" "4.264566,14.496572,1.497430")
(COMMAND "POINT" "4.340035,14.491845,1.527043")
(COMMAND "POINT" "4.417110,14.487049,1.554576")
(COMMAND "POINT" "4.495794,14.482184,1.580026")
(COMMAND "POINT" "4.576084,14.477250,1.603396")
(COMMAND "POINT" "4.657983,14.472247,1.624685")
(COMMAND "POINT" "4.741489,14.467174,1.643892")
(COMMAND "POINT" "4.826602,14.462033,1.661018")
(COMMAND "POINT" "4.913323,14.456822,1.676063")
(COMMAND "POINT" "5.001651,14.451542,1.689027")
(COMMAND "POINT" "5.091587,14.446193,1.699910")
(COMMAND "POINT" "5.183130,14.440775,1.708711")
(COMMAND "POINT" "5.276281,14.435288,1.715432")
(COMMAND "POINT" "5.371039,14.429732,1.720071")
(COMMAND "POINT" "5.467405,14.424107,1.722629")
(COMMAND "POINT" "5.565379,14.418412,1.723106")
(COMMAND "POINT" "5.664960,14.412649,1.721501")
(COMMAND "POINT" "5.766148,14.406816,1.717816")
(COMMAND "POINT" "5.868944,14.400914,1.712049")
(COMMAND "POINT" "5.973347,14.394944,1.704201")
(COMMAND "POINT" "6.079358,14.388904,1.694272")
(COMMAND "POINT" "6.186977,14.382795,1.682262")
(COMMAND "POINT" "6.296203,14.376616,1.668171")
(COMMAND "POINT" "6.407036,14.370369,1.651998")
(COMMAND "POINT" "6.519477,14.364053,1.633744")
(COMMAND "POINT" "6.633526,14.357667,1.613410")
(COMMAND "POINT" "6.749181,14.351213,1.590993")
(COMMAND "POINT" "6.866445,14.344689,1.566496")
(COMMAND "POINT" "6.985316,14.338096,1.539918")
(COMMAND "POINT" "7.105794,14.331434,1.511258")
(COMMAND "POINT" "7.227880,14.324703,1.480517")
(COMMAND "POINT" "7.351574,14.317903,1.447695")
(COMMAND "POINT" "7.476875,14.311034,1.412792")
(COMMAND "POINT" "7.603784,14.304095,1.375808")
(COMMAND "POINT" "7.732300,14.297088,1.336743")
(COMMAND "POINT" "7.862423,14.290011,1.295596")
(COMMAND "POINT" "7.994154,14.282866,1.252368")
(COMMAND "POINT" "8.127493,14.275651,1.207059")
(COMMAND "POINT" "8.262439,14.268367,1.159669")
(COMMAND "POINT" "8.398992,14.261014,1.110198")
(COMMAND "POINT" "8.537153,14.253592,1.058645")
(COMMAND "POINT" "8.676922,14.246101,1.005012")
(COMMAND "POINT" "8.817957,14.238765,0.949739")
(COMMAND "POINT" "8.958212,14.232933,0.895477")
(COMMAND "POINT" "9.097345,14.228828,0.842669")
(COMMAND "POINT" "9.235357,14.226452,0.791314")
(COMMAND "POINT" "9.372248,14.225803,0.741412")
(COMMAND "POINT" "9.508017,14.226882,0.692964")
(COMMAND "POINT" "9.642665,14.229690,0.645969")
(COMMAND "POINT" "9.776192,14.234225,0.600427")
(COMMAND "POINT" "9.908597,14.240488,0.556339")
(COMMAND "POINT" "10.039881,14.248479,0.513703")
(COMMAND "POINT" "10.170044,14.258198,0.472521")
(COMMAND "POINT" "10.299085,14.269645,0.432793")
(COMMAND "POINT" "10.427005,14.282820,0.394518")
(COMMAND "POINT" "10.553804,14.297723,0.357696")
(COMMAND "POINT" "10.679481,14.314354,0.322327")
(COMMAND "POINT" "10.804037,14.332712,0.288412")
(COMMAND "POINT" "10.927471,14.352799,0.255949")
(COMMAND "POINT" "11.049784,14.374613,0.224941")
(COMMAND "POINT" "11.170976,14.398156,0.195385")
(COMMAND "POINT" "11.291047,14.423426,0.167283")
(COMMAND "POINT" "11.409996,14.450425,0.140634")
(COMMAND "POINT" "11.527823,14.479151,0.115438")
(COMMAND "POINT" "11.644530,14.509605,0.091696")
(COMMAND "POINT" "11.760115,14.541787,0.069407")
(COMMAND "POINT" "11.874579,14.575697,0.048571")
(COMMAND "POINT" "11.987921,14.611335,0.029189")
(COMMAND "POINT" "12.100142,14.648701,0.011260")
(COMMAND "POINT" "12.211242,14.687795,-0.005216")
(COMMAND "POINT" "12.321220,14.728617,-0.020238")
(COMMAND "POINT" "12.430077,14.771167,-0.033808")
(COMMAND "POINT" "12.537812,14.815444,-0.045924")
(COMMAND "POINT" "12.644427,14.861450,-0.056586")
(COMMAND "POINT" "12.749920,14.909183,-0.065796")
(COMMAND "POINT" "12.854291,14.958645,-0.073552")
(COMMAND "POINT" "12.957541,15.009834,-0.079854")
(COMMAND "POINT" "13.059670,15.062752,-0.084704")
(COMMAND "POINT" "13.160678,15.117397,-0.088100")
(COMMAND "POINT" "13.260564,15.173770,-0.090043")
(COMMAND "POINT" "13.359329,15.231871,-0.090532")
(COMMAND "POINT" "13.456972,15.291700,-0.089569")
(COMMAND "POINT" "13.553494,15.353257,-0.087152")
(COMMAND "POINT" "13.648895,15.416542,-0.083281")
(COMMAND "POINT" "13.743174,15.481555,-0.077958")
(COMMAND "POINT" "13.836332,15.548296,-0.071181")
(COMMAND "POINT" "13.928369,15.616765,-0.062951")
(COMMAND "POINT" "14.019285,15.686961,-0.053267")
(COMMAND "POINT" "14.109079,15.758886,-0.042130")
(COMMAND "POINT" "14.197751,15.832538,-0.029540")
(COMMAND "POINT" "14.285302,15.907919,-0.015497")
(COMMAND "POINT" "14.371732,15.985027,0.000000")
(COMMAND "POINT" "3.644785,14.610730,1.239217")
(COMMAND "POINT" "3.704932,14.614185,1.287572")
(COMMAND "POINT" "3.766791,14.617353,1.333751")
(COMMAND "POINT" "3.830363,14.620232,1.377755")
(COMMAND "POINT" "3.895647,14.622823,1.419584")
(COMMAND "POINT" "3.962644,14.625125,1.459238")
(COMMAND "POINT" "4.031353,14.627140,1.496716")
(COMMAND "POINT" "4.101775,14.628866,1.532019")
(COMMAND "POINT" "4.173909,14.630304,1.565147")
(COMMAND "POINT" "4.247756,14.631454,1.596099")
(COMMAND "POINT" "4.323316,14.632315,1.624876")
(COMMAND "POINT" "4.400588,14.632889,1.651478")
(COMMAND "POINT" "4.479572,14.633174,1.675905")
(COMMAND "POINT" "4.560269,14.633171,1.698156")
(COMMAND "POINT" "4.642678,14.632880,1.718232")
(COMMAND "POINT" "4.726800,14.632300,1.736133")
(COMMAND "POINT" "4.812635,14.631433,1.751858")
(COMMAND "POINT" "4.900182,14.630277,1.765408")
(COMMAND "POINT" "4.989441,14.628833,1.776783")
(COMMAND "POINT" "5.080414,14.627100,1.785983")
(COMMAND "POINT" "5.173098,14.625080,1.793007")
(COMMAND "POINT" "5.267495,14.622771,1.797856")
(COMMAND "POINT" "5.363605,14.620174,1.800529")
(COMMAND "POINT" "5.461427,14.617289,1.801028")
(COMMAND "POINT" "5.560962,14.614116,1.799351")
(COMMAND "POINT" "5.662209,14.610654,1.795499")
(COMMAND "POINT" "5.765169,14.606905,1.789471")
(COMMAND "POINT" "5.869841,14.602867,1.781268")
(COMMAND "POINT" "5.976226,14.598541,1.770890")
(COMMAND "POINT" "6.084323,14.593926,1.758337")
(COMMAND "POINT" "6.194133,14.589024,1.743608")
(COMMAND "POINT" "6.305655,14.583833,1.726705")
(COMMAND "POINT" "6.418890,14.578354,1.707625")
(COMMAND "POINT" "6.533837,14.572587,1.686371")
(COMMAND "POINT" "6.650497,14.566531,1.662941")
(COMMAND "POINT" "6.768869,14.560187,1.637336")
(COMMAND "POINT" "6.888954,14.553556,1.609556")
(COMMAND "POINT" "7.010752,14.546636,1.579600")
(COMMAND "POINT" "7.134262,14.539427,1.547469")
(COMMAND "POINT" "7.259484,14.531931,1.513163")
(COMMAND "POINT" "7.386419,14.524146,1.476681")
(COMMAND "POINT" "7.515067,14.516073,1.438025")
(COMMAND "POINT" "7.645427,14.507712,1.397193")
(COMMAND "POINT" "7.777499,14.499063,1.354185")
(COMMAND "POINT" "7.911284,14.490125,1.309003")
(COMMAND "POINT" "8.046782,14.480900,1.261645")
(COMMAND "POINT" "8.183992,14.471386,1.212111")
(COMMAND "POINT" "8.322915,14.461583,1.160403")
(COMMAND "POINT" "8.463550,14.451493,1.106519")
(COMMAND "POINT" "8.605897,14.441115,1.050460")
(COMMAND "POINT" "8.749600,14.430703,0.992687")
(COMMAND "POINT" "8.892516,14.421788,0.935972")
(COMMAND "POINT" "9.034287,14.414624,0.880776")
(COMMAND "POINT" "9.174914,14.409213,0.827098")
(COMMAND "POINT" "9.314396,14.405553,0.774940")
(COMMAND "POINT" "9.452733,14.403645,0.724301")
(COMMAND "POINT" "9.589926,14.403488,0.675181")
(COMMAND "POINT" "9.725974,14.405084,0.627579")
(COMMAND "POINT" "9.860878,14.408431,0.581497")
(COMMAND "POINT" "9.994637,14.413529,0.536934")
(COMMAND "POINT" "10.127252,14.420380,0.493890")
(COMMAND "POINT" "10.258722,14.428982,0.452365")
(COMMAND "POINT" "10.389048,14.439336,0.412358")
(COMMAND "POINT" "10.518229,14.451441,0.373871")
(COMMAND "POINT" "10.646265,14.465299,0.336903")
(COMMAND "POINT" "10.773157,14.480908,0.301454")
(COMMAND "POINT" "10.898905,14.498269,0.267524")
(COMMAND "POINT" "11.023508,14.517381,0.235113")
(COMMAND "POINT" "11.146966,14.538245,0.204221")
(COMMAND "POINT" "11.269280,14.560861,0.174848")
(COMMAND "POINT" "11.390449,14.585229,0.146994")
(COMMAND "POINT" "11.510474,14.611349,0.120659")
(COMMAND "POINT" "11.629354,14.639220,0.095843")
(COMMAND "POINT" "11.747089,14.668843,0.072546")
(COMMAND "POINT" "11.863680,14.700217,0.050768")
(COMMAND "POINT" "11.979127,14.733343,0.030509")
(COMMAND "POINT" "12.093429,14.768221,0.011769")
(COMMAND "POINT" "12.206586,14.804851,-0.005452")
(COMMAND "POINT" "12.318599,14.843233,-0.021154")
(COMMAND "POINT" "12.429467,14.883366,-0.035337")
(COMMAND "POINT" "12.539191,14.925251,-0.048000")
(COMMAND "POINT" "12.647770,14.968888,-0.059145")
(COMMAND "POINT" "12.755205,15.014276,-0.068771")
(COMMAND "POINT" "12.861495,15.061416,-0.076878")
(COMMAND "POINT" "12.966640,15.110308,-0.083466")
(COMMAND "POINT" "13.070641,15.160951,-0.088534")
(COMMAND "POINT" "13.173498,15.213347,-0.092084")
(COMMAND "POINT" "13.275210,15.267494,-0.094115")
(COMMAND "POINT" "13.375777,15.323392,-0.094626")
(COMMAND "POINT" "13.475200,15.381043,-0.093619")
(COMMAND "POINT" "13.573478,15.440445,-0.091093")
(COMMAND "POINT" "13.670612,15.501599,-0.087047")
(COMMAND "POINT" "13.766601,15.564505,-0.081483")
(COMMAND "POINT" "13.861446,15.629162,-0.074400")
(COMMAND "POINT" "13.955146,15.695571,-0.065797")
(COMMAND "POINT" "14.047701,15.763732,-0.055676")
(COMMAND "POINT" "14.139112,15.833644,-0.044035")
(COMMAND "POINT" "14.229379,15.905309,-0.030876")
(COMMAND "POINT" "14.318500,15.978725,-0.016197")
(COMMAND "POINT" "14.406478,16.053892,0.000000")
(COMMAND "POINT" "3.572282,14.688861,1.293586")
(COMMAND "POINT" "3.629790,14.699936,1.344062")
(COMMAND "POINT" "3.689118,14.710502,1.392268")
(COMMAND "POINT" "3.750267,14.720559,1.438203")
(COMMAND "POINT" "3.813236,14.730108,1.481867")
(COMMAND "POINT" "3.878026,14.739148,1.523260")
(COMMAND "POINT" "3.944636,14.747679,1.562383")
(COMMAND "POINT" "4.013066,14.755701,1.599234")
(COMMAND "POINT" "4.083317,14.763215,1.633815")
(COMMAND "POINT" "4.155388,14.770220,1.666126")
(COMMAND "POINT" "4.229279,14.776716,1.696166")
(COMMAND "POINT" "4.304991,14.782703,1.723935")
(COMMAND "POINT" "4.382523,14.788182,1.749433")
(COMMAND "POINT" "4.461876,14.793152,1.772660")
(COMMAND "POINT" "4.543049,14.797613,1.793617")
(COMMAND "POINT" "4.626042,14.801565,1.812303")
(COMMAND "POINT" "4.710856,14.805009,1.828718")
(COMMAND "POINT" "4.797490,14.807943,1.842863")
(COMMAND "POINT" "4.885944,14.810369,1.854737")
(COMMAND "POINT" "4.976219,14.812287,1.864340")
(COMMAND "POINT" "5.068314,14.813695,1.871672")
(COMMAND "POINT" "5.162229,14.814595,1.876734")
(COMMAND "POINT" "5.257965,14.814986,1.879525")
(COMMAND "POINT" "5.355521,14.814868,1.880045")
(COMMAND "POINT" "5.454898,14.814241,1.878295")
(COMMAND "POINT" "5.556095,14.813106,1.874274")
(COMMAND "POINT" "5.659112,14.811462,1.867982")
(COMMAND "POINT" "5.763950,14.809309,1.859419")
(COMMAND "POINT" "5.870608,14.806648,1.848586")
(COMMAND "POINT" "5.979086,14.803477,1.835482")
(COMMAND "POINT" "6.089385,14.799798,1.820107")
(COMMAND "POINT" "6.201504,14.795610,1.802461")
(COMMAND "POINT" "6.315444,14.790914,1.782545")
(COMMAND "POINT" "6.431204,14.785708,1.760358")
(COMMAND "POINT" "6.548784,14.779994,1.735900")
(COMMAND "POINT" "6.668184,14.773771,1.709172")
(COMMAND "POINT" "6.789405,14.767039,1.680173")
(COMMAND "POINT" "6.912447,14.759799,1.648903")
(COMMAND "POINT" "7.037309,14.752050,1.615362")
(COMMAND "POINT" "7.163991,14.743792,1.579551")
(COMMAND "POINT" "7.292493,14.735025,1.541469")
(COMMAND "POINT" "7.422816,14.725750,1.501116")
(COMMAND "POINT" "7.554959,14.715965,1.458492")
(COMMAND "POINT" "7.688923,14.705672,1.413598")
(COMMAND "POINT" "7.824707,14.694870,1.366433")
(COMMAND "POINT" "7.962311,14.683560,1.316998")
(COMMAND "POINT" "8.101736,14.671741,1.265291")
(COMMAND "POINT" "8.242981,14.659413,1.211314")
(COMMAND "POINT" "8.386046,14.646576,1.155066")
(COMMAND "POINT" "8.530932,14.633230,1.096548")
(COMMAND "POINT" "8.677264,14.619661,1.036240")
(COMMAND "POINT" "8.822799,14.607582,0.977037")
(COMMAND "POINT" "8.967164,14.597277,0.919419")
(COMMAND "POINT" "9.110359,14.588748,0.863386")
(COMMAND "POINT" "9.252382,14.581994,0.808940")
(COMMAND "POINT" "9.393235,14.577014,0.756079")
(COMMAND "POINT" "9.532917,14.573809,0.704803")
(COMMAND "POINT" "9.671429,14.572380,0.655114")
(COMMAND "POINT" "9.808770,14.572725,0.607010")
(COMMAND "POINT" "9.944941,14.574846,0.560491")
(COMMAND "POINT" "10.079940,14.578741,0.515559")
(COMMAND "POINT" "10.213770,14.584411,0.472211")
(COMMAND "POINT" "10.346428,14.591857,0.430450")
(COMMAND "POINT" "10.477916,14.601077,0.390274")
(COMMAND "POINT" "10.608233,14.612072,0.351684")
(COMMAND "POINT" "10.737380,14.624842,0.314680")
(COMMAND "POINT" "10.865356,14.639387,0.279261")
(COMMAND "POINT" "10.992161,14.655707,0.245428")
(COMMAND "POINT" "11.117796,14.673802,0.213181")
(COMMAND "POINT" "11.242260,14.693673,0.182519")
(COMMAND "POINT" "11.365554,14.715318,0.153443")
(COMMAND "POINT" "11.487677,14.738738,0.125953")
(COMMAND "POINT" "11.608629,14.763932,0.100048")
(COMMAND "POINT" "11.728410,14.790902,0.075729")
(COMMAND "POINT" "11.847021,14.819647,0.052995")
(COMMAND "POINT" "11.964462,14.850167,0.031848")
(COMMAND "POINT" "12.080731,14.882462,0.012285")
(COMMAND "POINT" "12.195830,14.916532,-0.005691")
(COMMAND "POINT" "12.309759,14.952376,-0.022082")
(COMMAND "POINT" "12.422517,14.989996,-0.036887")
(COMMAND "POINT" "12.534104,15.029391,-0.050106")
(COMMAND "POINT" "12.644520,15.070561,-0.061740")
(COMMAND "POINT" "12.753766,15.113505,-0.071788")
(COMMAND "POINT" "12.861841,15.158225,-0.080251")
(COMMAND "POINT" "12.968746,15.204719,-0.087127")
(COMMAND "POINT" "13.074480,15.252989,-0.092419")
(COMMAND "POINT" "13.179043,15.303033,-0.096124")
(COMMAND "POINT" "13.282436,15.354853,-0.098244")
(COMMAND "POINT" "13.384658,15.408447,-0.098778")
(COMMAND "POINT" "13.485710,15.463817,-0.097727")
(COMMAND "POINT" "13.585590,15.520961,-0.095089")
(COMMAND "POINT" "13.684301,15.579880,-0.090867")
(COMMAND "POINT" "13.781840,15.640575,-0.085058")
(COMMAND "POINT" "13.878209,15.703044,-0.077664")
(COMMAND "POINT" "13.973407,15.767288,-0.068684")
(COMMAND "POINT" "14.067435,15.833307,-0.058119")
(COMMAND "POINT" "14.160292,15.901102,-0.045967")
(COMMAND "POINT" "14.251979,15.970671,-0.032231")
(COMMAND "POINT" "14.342494,16.042015,-0.016908")
(COMMAND "POINT" "14.431839,16.115134,0.000000")
(COMMAND "POINT" "3.501180,14.766292,1.348709")
(COMMAND "POINT" "3.555873,14.784976,1.401336")
(COMMAND "POINT" "3.612496,14.802930,1.451596")
(COMMAND "POINT" "3.671051,14.820152,1.499488")
(COMMAND "POINT" "3.731536,14.836644,1.545012")
(COMMAND "POINT" "3.793953,14.852406,1.588170")
(COMMAND "POINT" "3.858300,14.867436,1.628959")
(COMMAND "POINT" "3.924579,14.881736,1.667382")
(COMMAND "POINT" "3.992789,14.895305,1.703436")
(COMMAND "POINT" "4.062930,14.908143,1.737123")
(COMMAND "POINT" "4.135002,14.920251,1.768443")
(COMMAND "POINT" "4.209005,14.931627,1.797395")
(COMMAND "POINT" "4.284938,14.942273,1.823980")
(COMMAND "POINT" "4.362804,14.952189,1.848198")
(COMMAND "POINT" "4.442600,14.961373,1.870047")
(COMMAND "POINT" "4.524327,14.969827,1.889530")
(COMMAND "POINT" "4.607985,14.977550,1.906644")
(COMMAND "POINT" "4.693574,14.984542,1.921392")
(COMMAND "POINT" "4.781094,14.990803,1.933772")
(COMMAND "POINT" "4.870546,14.996334,1.943784")
(COMMAND "POINT" "4.961928,15.001134,1.951429")
(COMMAND "POINT" "5.055242,15.005203,1.956706")
(COMMAND "POINT" "5.150486,15.008541,1.959616")
(COMMAND "POINT" "5.247662,15.011149,1.960159")
(COMMAND "POINT" "5.346768,15.013025,1.958334")
(COMMAND "POINT" "5.447806,15.014171,1.954141")
(COMMAND "POINT" "5.550775,15.014587,1.947581")
(COMMAND "POINT" "5.655674,15.014271,1.938653")
(COMMAND "POINT" "5.762505,15.013225,1.927358")
(COMMAND "POINT" "5.871267,15.011448,1.913696")
(COMMAND "POINT" "5.981960,15.008940,1.897666")
(COMMAND "POINT" "6.094584,15.005702,1.879269")
(COMMAND "POINT" "6.209139,15.001732,1.858504")
(COMMAND "POINT" "6.325625,14.997032,1.835371")
(COMMAND "POINT" "6.444042,14.991602,1.809871")
(COMMAND "POINT" "6.564390,14.985440,1.782004")
(COMMAND "POINT" "6.686669,14.978548,1.751769")
(COMMAND "POINT" "6.810880,14.970924,1.719167")
(COMMAND "POINT" "6.937021,14.962571,1.684197")
(COMMAND "POINT" "7.065093,14.953486,1.646859")
(COMMAND "POINT" "7.195097,14.943671,1.607154")
(COMMAND "POINT" "7.327031,14.933124,1.565082")
(COMMAND "POINT" "7.460897,14.921848,1.520642")
(COMMAND "POINT" "7.596693,14.909840,1.473835")
(COMMAND "POINT" "7.734421,14.897101,1.424660")
(COMMAND "POINT" "7.874080,14.883632,1.373118")
(COMMAND "POINT" "8.015670,14.869432,1.319208")
(COMMAND "POINT" "8.159190,14.854501,1.262931")
(COMMAND "POINT" "8.304642,14.838840,1.204286")
(COMMAND "POINT" "8.452025,14.822448,1.143274")
(COMMAND "POINT" "8.600948,14.805641,1.080397")
(COMMAND "POINT" "8.749062,14.790315,1.018670")
(COMMAND "POINT" "8.895977,14.776788,0.958597")
(COMMAND "POINT" "9.041692,14.765058,0.900177")
(COMMAND "POINT" "9.186207,14.755125,0.843410")
(COMMAND "POINT" "9.329523,14.746991,0.788297")
(COMMAND "POINT" "9.471640,14.740654,0.734837")
(COMMAND "POINT" "9.612556,14.736114,0.683030")
(COMMAND "POINT" "9.752274,14.733372,0.632876")
(COMMAND "POINT" "9.890791,14.732428,0.584375")
(COMMAND "POINT" "10.028109,14.733282,0.537528")
(COMMAND "POINT" "10.164227,14.735933,0.492334")
(COMMAND "POINT" "10.299146,14.740382,0.448793")
(COMMAND "POINT" "10.432865,14.746629,0.406905")
(COMMAND "POINT" "10.565385,14.754673,0.366670")
(COMMAND "POINT" "10.696705,14.764515,0.328089")
(COMMAND "POINT" "10.826825,14.776155,0.291161")
(COMMAND "POINT" "10.955746,14.789592,0.255886")
(COMMAND "POINT" "11.083467,14.804827,0.222265")
(COMMAND "POINT" "11.209988,14.821860,0.190297")
(COMMAND "POINT" "11.335310,14.840690,0.159982")
(COMMAND "POINT" "11.459432,14.861318,0.131320")
(COMMAND "POINT" "11.582355,14.883743,0.104311")
(COMMAND "POINT" "11.704078,14.907967,0.078956")
(COMMAND "POINT" "11.824602,14.933988,0.055254")
(COMMAND "POINT" "11.943925,14.961806,0.033205")
(COMMAND "POINT" "12.062050,14.991423,0.012809")
(COMMAND "POINT" "12.178974,15.022836,-0.005933")
(COMMAND "POINT" "12.294699,15.056048,-0.023023")
(COMMAND "POINT" "12.409225,15.091057,-0.038459")
(COMMAND "POINT" "12.522551,15.127864,-0.052241")
(COMMAND "POINT" "12.634677,15.166469,-0.064371")
(COMMAND "POINT" "12.745604,15.206871,-0.074847")
(COMMAND "POINT" "12.855331,15.249071,-0.083670")
(COMMAND "POINT" "12.963858,15.293069,-0.090840")
(COMMAND "POINT" "13.071186,15.338864,-0.096357")
(COMMAND "POINT" "13.177314,15.386457,-0.100220")
(COMMAND "POINT" "13.282243,15.435847,-0.102430")
(COMMAND "POINT" "13.385972,15.487036,-0.102987")
(COMMAND "POINT" "13.488501,15.540022,-0.101891")
(COMMAND "POINT" "13.589831,15.594805,-0.099141")
(COMMAND "POINT" "13.689962,15.651386,-0.094739")
(COMMAND "POINT" "13.788892,15.709765,-0.088683")
(COMMAND "POINT" "13.886623,15.769942,-0.080973")
(COMMAND "POINT" "13.983155,15.831916,-0.071611")
(COMMAND "POINT" "14.078486,15.895688,-0.060595")
(COMMAND "POINT" "14.172619,15.961258,-0.047926")
(COMMAND "POINT" "14.265551,16.028625,-0.033604")
(COMMAND "POINT" "14.357284,16.097790,-0.017629")
(COMMAND "POINT" "14.447818,16.168752,0.000000")
(COMMAND "POINT" "3.431481,14.843023,1.404586")
(COMMAND "POINT" "3.483181,14.869307,1.459393")
(COMMAND "POINT" "3.536925,14.894636,1.511735")
(COMMAND "POINT" "3.592713,14.919011,1.561611")
(COMMAND "POINT" "3.650547,14.942432,1.609022")
(COMMAND "POINT" "3.710425,14.964899,1.653967")
(COMMAND "POINT" "3.772347,14.986412,1.696447")
(COMMAND "POINT" "3.836314,15.006970,1.736461")
(COMMAND "POINT" "3.902326,15.026574,1.774009")
(COMMAND "POINT" "3.970382,15.045224,1.809092")
(COMMAND "POINT" "4.040482,15.062920,1.841709")
(COMMAND "POINT" "4.112628,15.079662,1.871861")
(COMMAND "POINT" "4.186818,15.095449,1.899547")
(COMMAND "POINT" "4.263052,15.110282,1.924768")
(COMMAND "POINT" "4.341331,15.124161,1.947523")
(COMMAND "POINT" "4.421655,15.137085,1.967812")
(COMMAND "POINT" "4.504023,15.149056,1.985636")
(COMMAND "POINT" "4.588436,15.160072,2.000994")
(COMMAND "POINT" "4.674893,15.170134,2.013887")
(COMMAND "POINT" "4.763395,15.179242,2.024314")
(COMMAND "POINT" "4.853941,15.187396,2.032276")
(COMMAND "POINT" "4.946532,15.194595,2.037772")
(COMMAND "POINT" "5.041168,15.200840,2.040803")
(COMMAND "POINT" "5.137848,15.206131,2.041367")
(COMMAND "POINT" "5.236573,15.210468,2.039467")
(COMMAND "POINT" "5.337342,15.213850,2.035100")
(COMMAND "POINT" "5.440156,15.216279,2.028269")
(COMMAND "POINT" "5.545014,15.217753,2.018971")
(COMMAND "POINT" "5.651917,15.218273,2.007208")
(COMMAND "POINT" "5.760865,15.217838,1.992980")
(COMMAND "POINT" "5.871857,15.216450,1.976286")
(COMMAND "POINT" "5.984894,15.214107,1.957126")
(COMMAND "POINT" "6.099975,15.210810,1.935501")
(COMMAND "POINT" "6.217101,15.206559,1.911410")
(COMMAND "POINT" "6.336272,15.201354,1.884854")
(COMMAND "POINT" "6.457487,15.195194,1.855832")
(COMMAND "POINT" "6.580746,15.188080,1.824344")
(COMMAND "POINT" "6.706050,15.180012,1.790391")
(COMMAND "POINT" "6.833399,15.170990,1.753972")
(COMMAND "POINT" "6.962793,15.161013,1.715088")
(COMMAND "POINT" "7.094230,15.150083,1.673738")
(COMMAND "POINT" "7.227713,15.138198,1.629923")
(COMMAND "POINT" "7.363240,15.125359,1.583642")
(COMMAND "POINT" "7.500812,15.111565,1.534896")
(COMMAND "POINT" "7.640428,15.096818,1.483683")
(COMMAND "POINT" "7.782089,15.081116,1.430006")
(COMMAND "POINT" "7.925794,15.064460,1.373863")
(COMMAND "POINT" "8.071544,15.046850,1.315254")
(COMMAND "POINT" "8.219338,15.028286,1.254179")
(COMMAND "POINT" "8.369177,15.008767,1.190640")
(COMMAND "POINT" "8.520652,14.988641,1.125157")
(COMMAND "POINT" "8.671304,14.969988,1.060874")
(COMMAND "POINT" "8.820725,14.953155,0.998312")
(COMMAND "POINT" "8.968914,14.938142,0.937471")
(COMMAND "POINT" "9.115872,14.924948,0.878353")
(COMMAND "POINT" "9.261598,14.913574,0.820956")
(COMMAND "POINT" "9.406093,14.904020,0.765281")
(COMMAND "POINT" "9.549356,14.896286,0.711327")
(COMMAND "POINT" "9.691388,14.890372,0.659096")
(COMMAND "POINT" "9.832189,14.886278,0.608586")
(COMMAND "POINT" "9.971758,14.884003,0.559797")
(COMMAND "POINT" "10.110095,14.883548,0.512731")
(COMMAND "POINT" "10.247201,14.884913,0.467386")
(COMMAND "POINT" "10.383076,14.888098,0.423763")
(COMMAND "POINT" "10.517719,14.893102,0.381861")
(COMMAND "POINT" "10.651131,14.899927,0.341682")
(COMMAND "POINT" "10.783311,14.908571,0.303224")
(COMMAND "POINT" "10.914260,14.919035,0.266488")
(COMMAND "POINT" "11.043978,14.931319,0.231473")
(COMMAND "POINT" "11.172464,14.945423,0.198181")
(COMMAND "POINT" "11.299718,14.961346,0.166610")
(COMMAND "POINT" "11.425741,14.979090,0.136760")
(COMMAND "POINT" "11.550533,14.998653,0.108633")
(COMMAND "POINT" "11.674093,15.020036,0.082227")
(COMMAND "POINT" "11.796421,15.043238,0.057543")
(COMMAND "POINT" "11.917518,15.068261,0.034580")
(COMMAND "POINT" "12.037384,15.095103,0.013340")
(COMMAND "POINT" "12.156018,15.123766,-0.006179")
(COMMAND "POINT" "12.273421,15.154248,-0.023977")
(COMMAND "POINT" "12.389592,15.186549,-0.040052")
(COMMAND "POINT" "12.504532,15.220671,-0.054406")
(COMMAND "POINT" "12.618241,15.256613,-0.067038")
(COMMAND "POINT" "12.730718,15.294374,-0.077948")
(COMMAND "POINT" "12.841963,15.333955,-0.087137")
(COMMAND "POINT" "12.951977,15.375356,-0.094604")
(COMMAND "POINT" "13.060760,15.418577,-0.100349")
(COMMAND "POINT" "13.168311,15.463617,-0.104372")
(COMMAND "POINT" "13.274630,15.510477,-0.106674")
(COMMAND "POINT" "13.379719,15.559158,-0.107254")
(COMMAND "POINT" "13.483575,15.609658,-0.106112")
(COMMAND "POINT" "13.586201,15.661977,-0.103249")
(COMMAND "POINT" "13.687595,15.716117,-0.098664")
(COMMAND "POINT" "13.787757,15.772076,-0.092357")
(COMMAND "POINT" "13.886688,15.829856,-0.084328")
(COMMAND "POINT" "13.984387,15.889455,-0.074578")
(COMMAND "POINT" "14.080855,15.950874,-0.063106")
(COMMAND "POINT" "14.176092,16.014112,-0.049912")
(COMMAND "POINT" "14.270097,16.079171,-0.034996")
(COMMAND "POINT" "14.362870,16.146049,-0.018359")
(COMMAND "POINT" "14.454412,16.214747,0.000000")
(COMMAND "POINT" "3.363184,14.919055,1.461216")
(COMMAND "POINT" "3.411713,14.952928,1.518233")
(COMMAND "POINT" "3.462404,14.985622,1.572685")
(COMMAND "POINT" "3.515255,15.017136,1.624573")
(COMMAND "POINT" "3.570268,15.047472,1.673895")
(COMMAND "POINT" "3.627441,15.076628,1.720652")
(COMMAND "POINT" "3.686775,15.104605,1.764844")
(COMMAND "POINT" "3.748271,15.131404,1.806472")
(COMMAND "POINT" "3.811927,15.157023,1.845534")
(COMMAND "POINT" "3.877744,15.181463,1.882031")
(COMMAND "POINT" "3.945722,15.204724,1.915964")
(COMMAND "POINT" "4.015861,15.226805,1.947331")
(COMMAND "POINT" "4.088161,15.247708,1.976134")
(COMMAND "POINT" "4.162621,15.267431,2.002371")
(COMMAND "POINT" "4.239243,15.285976,2.026044")
(COMMAND "POINT" "4.318026,15.303341,2.047151")
(COMMAND "POINT" "4.398969,15.319527,2.065694")
(COMMAND "POINT" "4.482074,15.334534,2.081671")
(COMMAND "POINT" "4.567339,15.348362,2.095084")
(COMMAND "POINT" "4.654765,15.361011,2.105931")
(COMMAND "POINT" "4.744353,15.372481,2.114214")
(COMMAND "POINT" "4.836101,15.382771,2.119931")
(COMMAND "POINT" "4.930010,15.391883,2.123084")
(COMMAND "POINT" "5.026080,15.399815,2.123672")
(COMMAND "POINT" "5.124311,15.406569,2.121694")
(COMMAND "POINT" "5.224703,15.412143,2.117152")
(COMMAND "POINT" "5.327256,15.416538,2.110045")
(COMMAND "POINT" "5.431970,15.419754,2.100373")
(COMMAND "POINT" "5.538845,15.421791,2.088135")
(COMMAND "POINT" "5.647880,15.422648,2.073333")
(COMMAND "POINT" "5.759077,15.422327,2.055966")
(COMMAND "POINT" "5.872434,15.420826,2.036034")
(COMMAND "POINT" "5.987953,15.418147,2.013537")
(COMMAND "POINT" "6.105632,15.414288,1.988475")
(COMMAND "POINT" "6.225473,15.409250,1.960848")
(COMMAND "POINT" "6.347474,15.403033,1.930656")
(COMMAND "POINT" "6.471636,15.395637,1.897899")
(COMMAND "POINT" "6.597959,15.387062,1.862577")
(COMMAND "POINT" "6.726443,15.377307,1.824690")
(COMMAND "POINT" "6.857088,15.366374,1.784238")
(COMMAND "POINT" "6.989894,15.354261,1.741221")
(COMMAND "POINT" "7.124861,15.340970,1.695639")
(COMMAND "POINT" "7.261989,15.326499,1.647492")
(COMMAND "POINT" "7.401277,15.310849,1.596780")
(COMMAND "POINT" "7.542727,15.294020,1.543503")
(COMMAND "POINT" "7.686337,15.276012,1.487661")
(COMMAND "POINT" "7.832109,15.256825,1.429254")
(COMMAND "POINT" "7.980041,15.236458,1.368283")
(COMMAND "POINT" "8.130135,15.214913,1.304746")
(COMMAND "POINT" "8.282389,15.192188,1.238644")
(COMMAND "POINT" "8.436376,15.168662,1.170522")
(COMMAND "POINT" "8.589525,15.146600,1.103646")
(COMMAND "POINT" "8.741408,15.126379,1.038562")
(COMMAND "POINT" "8.892024,15.108000,0.975269")
(COMMAND "POINT" "9.041375,15.091462,0.913766")
(COMMAND "POINT" "9.189459,15.076765,0.854055")
(COMMAND "POINT" "9.336277,15.063910,0.796135")
(COMMAND "POINT" "9.481829,15.052896,0.740007")
(COMMAND "POINT" "9.626114,15.043724,0.685669")
(COMMAND "POINT" "9.769134,15.036393,0.633123")
(COMMAND "POINT" "9.910887,15.030903,0.582367")
(COMMAND "POINT" "10.051374,15.027255,0.533403")
(COMMAND "POINT" "10.190594,15.025449,0.486230")
(COMMAND "POINT" "10.328549,15.025483,0.440848")
(COMMAND "POINT" "10.465237,15.027360,0.397257")
(COMMAND "POINT" "10.600660,15.031077,0.355458")
(COMMAND "POINT" "10.734816,15.036636,0.315449")
(COMMAND "POINT" "10.867705,15.044037,0.277232")
(COMMAND "POINT" "10.999329,15.053278,0.240806")
(COMMAND "POINT" "11.129686,15.064362,0.206171")
(COMMAND "POINT" "11.258777,15.077286,0.173327")
(COMMAND "POINT" "11.386602,15.092053,0.142274")
(COMMAND "POINT" "11.513161,15.108660,0.113013")
(COMMAND "POINT" "11.638454,15.127109,0.085542")
(COMMAND "POINT" "11.762480,15.147399,0.059863")
(COMMAND "POINT" "11.885240,15.169531,0.035975")
(COMMAND "POINT" "12.006734,15.193504,0.013877")
(COMMAND "POINT" "12.126962,15.219319,-0.006428")
(COMMAND "POINT" "12.245924,15.246975,-0.024943")
(COMMAND "POINT" "12.363619,15.276472,-0.041667")
(COMMAND "POINT" "12.480048,15.307811,-0.056599")
(COMMAND "POINT" "12.595211,15.340991,-0.069741")
(COMMAND "POINT" "12.709108,15.376013,-0.081091")
(COMMAND "POINT" "12.821738,15.412876,-0.090650")
(COMMAND "POINT" "12.933103,15.451581,-0.098418")
(COMMAND "POINT" "13.043201,15.492127,-0.104395")
(COMMAND "POINT" "13.152033,15.534514,-0.108580")
(COMMAND "POINT" "13.259599,15.578743,-0.110975")
(COMMAND "POINT" "13.365898,15.624813,-0.111578")
(COMMAND "POINT" "13.470931,15.672725,-0.110390")
(COMMAND "POINT" "13.574699,15.722478,-0.107412")
(COMMAND "POINT" "13.677199,15.774072,-0.102642")
(COMMAND "POINT" "13.778434,15.827508,-0.096080")
(COMMAND "POINT" "13.878403,15.882785,-0.087728")
(COMMAND "POINT" "13.977105,15.939904,-0.077585")
(COMMAND "POINT" "14.074541,15.998864,-0.065650")
(COMMAND "POINT" "14.170711,16.059666,-0.051924")
(COMMAND "POINT" "14.265615,16.122309,-0.036407")
(COMMAND "POINT" "14.359252,16.186793,-0.019099")
(COMMAND "POINT" "14.451624,16.253119,0.000000")
(COMMAND "POINT" "3.296289,14.994387,1.518600")
(COMMAND "POINT" "3.341471,15.035839,1.577857")
(COMMAND "POINT" "3.388934,15.075886,1.634447")
(COMMAND "POINT" "3.438677,15.114527,1.688372")
(COMMAND "POINT" "3.490700,15.151762,1.739631")
(COMMAND "POINT" "3.545003,15.187593,1.788225")
(COMMAND "POINT" "3.601586,15.222017,1.834153")
(COMMAND "POINT" "3.660449,15.255037,1.877415")
(COMMAND "POINT" "3.721592,15.286650,1.918011")
(COMMAND "POINT" "3.785016,15.316859,1.955942")
(COMMAND "POINT" "3.850720,15.345661,1.991207")
(COMMAND "POINT" "3.918703,15.373059,2.023806")
(COMMAND "POINT" "3.988967,15.399051,2.053740")
(COMMAND "POINT" "4.061511,15.423637,2.081007")
(COMMAND "POINT" "4.136336,15.446818,2.105610")
(COMMAND "POINT" "4.213440,15.468594,2.127546")
(COMMAND "POINT" "4.292824,15.488964,2.146817")
(COMMAND "POINT" "4.374489,15.507928,2.163422")
(COMMAND "POINT" "4.458433,15.525488,2.177361")
(COMMAND "POINT" "4.544658,15.541641,2.188635")
(COMMAND "POINT" "4.633163,15.556390,2.197242")
(COMMAND "POINT" "4.723948,15.569732,2.203185")
(COMMAND "POINT" "4.817013,15.581670,2.206461")
(COMMAND "POINT" "4.912359,15.592201,2.207072")
(COMMAND "POINT" "5.009984,15.601328,2.205017")
(COMMAND "POINT" "5.109889,15.609049,2.200296")
(COMMAND "POINT" "5.212075,15.615364,2.192910")
(COMMAND "POINT" "5.316541,15.620274,2.182858")
(COMMAND "POINT" "5.423287,15.623779,2.170140")
(COMMAND "POINT" "5.532313,15.625878,2.154756")
(COMMAND "POINT" "5.643619,15.626571,2.136707")
(COMMAND "POINT" "5.757205,15.625859,2.115992")
(COMMAND "POINT" "5.873072,15.623742,2.092612")
(COMMAND "POINT" "5.991218,15.620219,2.066565")
(COMMAND "POINT" "6.111645,15.615291,2.037853")
(COMMAND "POINT" "6.234352,15.608957,2.006476")
(COMMAND "POINT" "6.359338,15.601218,1.972432")
(COMMAND "POINT" "6.486605,15.592073,1.935723")
(COMMAND "POINT" "6.616153,15.581523,1.896348")
(COMMAND "POINT" "6.747980,15.569568,1.854307")
(COMMAND "POINT" "6.882087,15.556207,1.809601")
(COMMAND "POINT" "7.018475,15.541440,1.762229")
(COMMAND "POINT" "7.157142,15.525268,1.712191")
(COMMAND "POINT" "7.298090,15.507691,1.659488")
(COMMAND "POINT" "7.441318,15.488708,1.604119")
(COMMAND "POINT" "7.586826,15.468320,1.546084")
(COMMAND "POINT" "7.734614,15.446526,1.485383")
(COMMAND "POINT" "7.884683,15.423327,1.422017")
(COMMAND "POINT" "8.037031,15.398722,1.355985")
(COMMAND "POINT" "8.191659,15.372712,1.287288")
(COMMAND "POINT" "8.348120,15.345704,1.216490")
(COMMAND "POINT" "8.503725,15.320151,1.146988")
(COMMAND "POINT" "8.658026,15.296461,1.079348")
(COMMAND "POINT" "8.811023,15.274632,1.013569")
(COMMAND "POINT" "8.962716,15.254666,0.949651")
(COMMAND "POINT" "9.113106,15.236563,0.887595")
(COMMAND "POINT" "9.262191,15.220322,0.827401")
(COMMAND "POINT" "9.409973,15.205944,0.769068")
(COMMAND "POINT" "9.556451,15.193428,0.712596")
(COMMAND "POINT" "9.701625,15.182775,0.657986")
(COMMAND "POINT" "9.845496,15.173984,0.605238")
(COMMAND "POINT" "9.988062,15.167055,0.554351")
(COMMAND "POINT" "10.129325,15.161989,0.505325")
(COMMAND "POINT" "10.269284,15.158786,0.458161")
(COMMAND "POINT" "10.407939,15.157445,0.412858")
(COMMAND "POINT" "10.545290,15.157966,0.369417")
(COMMAND "POINT" "10.681337,15.160350,0.327838")
(COMMAND "POINT" "10.816081,15.164597,0.288119")
(COMMAND "POINT" "10.949521,15.170705,0.250263")
(COMMAND "POINT" "11.081657,15.178677,0.214267")
(COMMAND "POINT" "11.212489,15.188511,0.180134")
(COMMAND "POINT" "11.342017,15.200207,0.147862")
(COMMAND "POINT" "11.470241,15.213766,0.117451")
(COMMAND "POINT" "11.597162,15.229187,0.088901")
(COMMAND "POINT" "11.722778,15.246471,0.062214")
(COMMAND "POINT" "11.847091,15.265617,0.037387")
(COMMAND "POINT" "11.970100,15.286625,0.014422")
(COMMAND "POINT" "12.091806,15.309497,-0.006681")
(COMMAND "POINT" "12.212207,15.334230,-0.025923")
(COMMAND "POINT" "12.331305,15.360826,-0.043303")
(COMMAND "POINT" "12.449098,15.389285,-0.058822")
(COMMAND "POINT" "12.565588,15.419606,-0.072480")
(COMMAND "POINT" "12.680774,15.451789,-0.084276")
(COMMAND "POINT" "12.794656,15.485835,-0.094210")
(COMMAND "POINT" "12.907235,15.521744,-0.102283")
(COMMAND "POINT" "13.018509,15.559515,-0.108494")
(COMMAND "POINT" "13.128480,15.599148,-0.112845")
(COMMAND "POINT" "13.237147,15.640644,-0.115333")
(COMMAND "POINT" "13.344510,15.684002,-0.115960")
(COMMAND "POINT" "13.450570,15.729223,-0.114726")
(COMMAND "POINT" "13.555325,15.776306,-0.111630")
(COMMAND "POINT" "13.658777,15.825252,-0.106672")
(COMMAND "POINT" "13.760924,15.876060,-0.099854")
(COMMAND "POINT" "13.861768,15.928731,-0.091173")
(COMMAND "POINT" "13.961308,15.983264,-0.080631")
(COMMAND "POINT" "14.059545,16.039660,-0.068228")
(COMMAND "POINT" "14.156477,16.097918,-0.053963")
(COMMAND "POINT" "14.252106,16.158039,-0.037837")
(COMMAND "POINT" "14.346431,16.220022,-0.019849")
(COMMAND "POINT" "14.439451,16.283867,0.000000")
(COMMAND "POINT" "3.230796,15.069020,1.576738")
(COMMAND "POINT" "3.272454,15.118041,1.638263")
(COMMAND "POINT" "3.316514,15.165429,1.697020")
(COMMAND "POINT" "3.362977,15.211183,1.753010")
(COMMAND "POINT" "3.411842,15.255305,1.806231")
(COMMAND "POINT" "3.463109,15.297793,1.856685")
(COMMAND "POINT" "3.516778,15.338647,1.904371")
(COMMAND "POINT" "3.572849,15.377869,1.949290")
(COMMAND "POINT" "3.631323,15.415457,1.991440")
(COMMAND "POINT" "3.692198,15.451412,2.030823")
(COMMAND "POINT" "3.755476,15.485734,2.067438")
(COMMAND "POINT" "3.821156,15.518422,2.101285")
(COMMAND "POINT" "3.889238,15.549477,2.132365")
(COMMAND "POINT" "3.959722,15.578899,2.160677")
(COMMAND "POINT" "4.032609,15.606688,2.186221")
(COMMAND "POINT" "4.107897,15.632843,2.208997")
(COMMAND "POINT" "4.185588,15.657366,2.229005")
(COMMAND "POINT" "4.265681,15.680255,2.246246")
(COMMAND "POINT" "4.348176,15.701510,2.260719")
(COMMAND "POINT" "4.433073,15.721133,2.272424")
(COMMAND "POINT" "4.520372,15.739122,2.281362")
(COMMAND "POINT" "4.610073,15.755477,2.287531")
(COMMAND "POINT" "4.702177,15.770200,2.290933")
(COMMAND "POINT" "4.796683,15.783289,2.291567")
(COMMAND "POINT" "4.893591,15.794745,2.289434")
(COMMAND "POINT" "4.992901,15.804568,2.284532")
(COMMAND "POINT" "5.094613,15.812758,2.276863")
(COMMAND "POINT" "5.198727,15.819314,2.266426")
(COMMAND "POINT" "5.305244,15.824237,2.253222")
(COMMAND "POINT" "5.414163,15.827527,2.237249")
(COMMAND "POINT" "5.525483,15.829183,2.218509")
(COMMAND "POINT" "5.639206,15.829206,2.197001")
(COMMAND "POINT" "5.755332,15.827596,2.172725")
(COMMAND "POINT" "5.873859,15.824353,2.145682")
(COMMAND "POINT" "5.994788,15.819477,2.115870")
(COMMAND "POINT" "6.118120,15.812967,2.083291")
(COMMAND "POINT" "6.243854,15.804824,2.047945")
(COMMAND "POINT" "6.371990,15.795047,2.009830")
(COMMAND "POINT" "6.502528,15.783638,1.968948")
(COMMAND "POINT" "6.635468,15.770595,1.925298")
(COMMAND "POINT" "6.770810,15.755919,1.878880")
(COMMAND "POINT" "6.908555,15.739609,1.829694")
(COMMAND "POINT" "7.048702,15.721667,1.777741")
(COMMAND "POINT" "7.191251,15.702091,1.723020")
(COMMAND "POINT" "7.336202,15.680882,1.665531")
(COMMAND "POINT" "7.483555,15.658039,1.605274")
(COMMAND "POINT" "7.633310,15.633563,1.542250")
(COMMAND "POINT" "7.785468,15.607454,1.476458")
(COMMAND "POINT" "7.940027,15.579712,1.407898")
(COMMAND "POINT" "8.096989,15.550337,1.336570")
(COMMAND "POINT" "8.255885,15.519767,1.263062")
(COMMAND "POINT" "8.413904,15.490642,1.190900")
(COMMAND "POINT" "8.570580,15.463399,1.120670")
(COMMAND "POINT" "8.725910,15.438039,1.052372")
(COMMAND "POINT" "8.879897,15.414562,0.986008")
(COMMAND "POINT" "9.032539,15.392968,0.921576")
(COMMAND "POINT" "9.183837,15.373258,0.859077")
(COMMAND "POINT" "9.333791,15.355430,0.798511")
(COMMAND "POINT" "9.482400,15.339485,0.739877")
(COMMAND "POINT" "9.629665,15.325423,0.683177")
(COMMAND "POINT" "9.775585,15.313244,0.628409")
(COMMAND "POINT" "9.920161,15.302948,0.575574")
(COMMAND "POINT" "10.063393,15.294535,0.524671")
(COMMAND "POINT" "10.205281,15.288005,0.475701")
(COMMAND "POINT" "10.345824,15.283358,0.428664")
(COMMAND "POINT" "10.485022,15.280594,0.383560")
(COMMAND "POINT" "10.622877,15.279713,0.340389")
(COMMAND "POINT" "10.759387,15.280715,0.299150")
(COMMAND "POINT" "10.894553,15.283600,0.259844")
(COMMAND "POINT" "11.028374,15.288368,0.222471")
(COMMAND "POINT" "11.160851,15.295019,0.187030")
(COMMAND "POINT" "11.291984,15.303553,0.153522")
(COMMAND "POINT" "11.421772,15.313969,0.121947")
(COMMAND "POINT" "11.550216,15.326269,0.092305")
(COMMAND "POINT" "11.677316,15.340452,0.064595")
(COMMAND "POINT" "11.803071,15.356518,0.038819")
(COMMAND "POINT" "11.927482,15.374467,0.014975")
(COMMAND "POINT" "12.050549,15.394298,-0.006937")
(COMMAND "POINT" "12.172271,15.416013,-0.026915")
(COMMAND "POINT" "12.292649,15.439611,-0.044961")
(COMMAND "POINT" "12.411683,15.465092,-0.061074")
(COMMAND "POINT" "12.529372,15.492455,-0.075254")
(COMMAND "POINT" "12.645717,15.521702,-0.087502")
(COMMAND "POINT" "12.760717,15.552832,-0.097817")
(COMMAND "POINT" "12.874374,15.585844,-0.106199")
(COMMAND "POINT" "12.986686,15.620740,-0.112648")
(COMMAND "POINT" "13.097653,15.657519,-0.117165")
(COMMAND "POINT" "13.207276,15.696180,-0.119748")
(COMMAND "POINT" "13.315555,15.736725,-0.120400")
(COMMAND "POINT" "13.422490,15.779152,-0.119118")
(COMMAND "POINT" "13.528080,15.823463,-0.115903")
(COMMAND "POINT" "13.632326,15.869656,-0.110756")
(COMMAND "POINT" "13.735227,15.917733,-0.103676")
(COMMAND "POINT" "13.836784,15.967692,-0.094664")
(COMMAND "POINT" "13.936997,16.019535,-0.083718")
(COMMAND "POINT" "14.035865,16.073260,-0.070840")
(COMMAND "POINT" "14.133390,16.128869,-0.056029")
(COMMAND "POINT" "14.229569,16.186360,-0.039286")
(COMMAND "POINT" "14.324405,16.245735,-0.020609")
(COMMAND "POINT" "14.417896,16.306992,0.000000")
(COMMAND "POINT" "3.166705,15.142953,1.635630")
(COMMAND "POINT" "3.204662,15.199533,1.699453")
(COMMAND "POINT" "3.245146,15.254250,1.760405")
(COMMAND "POINT" "3.288157,15.307105,1.818486")
(COMMAND "POINT" "3.333695,15.358098,1.873695")
(COMMAND "POINT" "3.381760,15.407228,1.926033")
(COMMAND "POINT" "3.432352,15.454495,1.975501")
(COMMAND "POINT" "3.485471,15.499900,2.022097")
(COMMAND "POINT" "3.541118,15.543443,2.065822")
(COMMAND "POINT" "3.599291,15.585123,2.106675")
(COMMAND "POINT" "3.659991,15.624940,2.144658")
(COMMAND "POINT" "3.723218,15.662895,2.179769")
(COMMAND "POINT" "3.788973,15.698988,2.212010")
(COMMAND "POINT" "3.857254,15.733218,2.241379")
(COMMAND "POINT" "3.928062,15.765585,2.267877")
(COMMAND "POINT" "4.001398,15.796090,2.291504")
(COMMAND "POINT" "4.077260,15.824733,2.312260")
(COMMAND "POINT" "4.155649,15.851512,2.330144")
(COMMAND "POINT" "4.236566,15.876430,2.345158")
(COMMAND "POINT" "4.320009,15.899485,2.357300")
(COMMAND "POINT" "4.405980,15.920677,2.366572")
(COMMAND "POINT" "4.494477,15.940007,2.372972")
(COMMAND "POINT" "4.585502,15.957474,2.376501")
(COMMAND "POINT" "4.679053,15.973079,2.377158")
(COMMAND "POINT" "4.775132,15.986821,2.374945")
(COMMAND "POINT" "4.873737,15.998701,2.369861")
(COMMAND "POINT" "4.974870,16.008719,2.361905")
(COMMAND "POINT" "5.078529,16.016873,2.351078")
(COMMAND "POINT" "5.184716,16.023166,2.337380")
(COMMAND "POINT" "5.293430,16.027595,2.320811")
(COMMAND "POINT" "5.404670,16.030163,2.301371")
(COMMAND "POINT" "5.518438,16.030867,2.279060")
(COMMAND "POINT" "5.634733,16.029710,2.253878")
(COMMAND "POINT" "5.753555,16.026689,2.225824")
(COMMAND "POINT" "5.874903,16.021807,2.194899")
(COMMAND "POINT" "5.998779,16.015061,2.161103")
(COMMAND "POINT" "6.125182,16.006454,2.124436")
(COMMAND "POINT" "6.254112,15.995983,2.084898")
(COMMAND "POINT" "6.385569,15.983650,2.042489")
(COMMAND "POINT" "6.519553,15.969455,1.997209")
(COMMAND "POINT" "6.656063,15.953397,1.949057")
(COMMAND "POINT" "6.795101,15.935477,1.898034")
(COMMAND "POINT" "6.936666,15.915694,1.844140")
(COMMAND "POINT" "7.080758,15.894049,1.787375")
(COMMAND "POINT" "7.227377,15.870541,1.727739")
(COMMAND "POINT" "7.376523,15.845170,1.665232")
(COMMAND "POINT" "7.528196,15.817937,1.599854")
(COMMAND "POINT" "7.682396,15.788842,1.531604")
(COMMAND "POINT" "7.839124,15.757884,1.460483")
(COMMAND "POINT" "7.998378,15.725064,1.386492")
(COMMAND "POINT" "8.159669,15.690851,1.310238")
(COMMAND "POINT" "8.320063,15.658071,1.235380")
(COMMAND "POINT" "8.479068,15.627194,1.162527")
(COMMAND "POINT" "8.636686,15.598220,1.091679")
(COMMAND "POINT" "8.792916,15.571149,1.022836")
(COMMAND "POINT" "8.947759,15.545981,0.955997")
(COMMAND "POINT" "9.101214,15.522716,0.891164")
(COMMAND "POINT" "9.253280,15.501353,0.828336")
(COMMAND "POINT" "9.403960,15.481894,0.767512")
(COMMAND "POINT" "9.553251,15.464337,0.708694")
(COMMAND "POINT" "9.701155,15.448684,0.651880")
(COMMAND "POINT" "9.847671,15.434933,0.597071")
(COMMAND "POINT" "9.992799,15.423086,0.544268")
(COMMAND "POINT" "10.136539,15.413141,0.493469")
(COMMAND "POINT" "10.278892,15.405099,0.444675")
(COMMAND "POINT" "10.419857,15.398960,0.397886")
(COMMAND "POINT" "10.559434,15.394725,0.353102")
(COMMAND "POINT" "10.697624,15.392392,0.310323")
(COMMAND "POINT" "10.834425,15.391962,0.269549")
(COMMAND "POINT" "10.969839,15.393435,0.230780")
(COMMAND "POINT" "11.103865,15.396811,0.194016")
(COMMAND "POINT" "11.236504,15.402090,0.159256")
(COMMAND "POINT" "11.367755,15.409271,0.126502")
(COMMAND "POINT" "11.497618,15.418356,0.095753")
(COMMAND "POINT" "11.626093,15.429344,0.067008")
(COMMAND "POINT" "11.753180,15.442235,0.040269")
(COMMAND "POINT" "11.878880,15.457028,0.015534")
(COMMAND "POINT" "12.003192,15.473725,-0.007196")
(COMMAND "POINT" "12.126116,15.492324,-0.027921")
(COMMAND "POINT" "12.247653,15.512827,-0.046640")
(COMMAND "POINT" "12.367802,15.535232,-0.063355")
(COMMAND "POINT" "12.486563,15.559540,-0.078065")
(COMMAND "POINT" "12.603936,15.585752,-0.090770")
(COMMAND "POINT" "12.719921,15.613866,-0.101470")
(COMMAND "POINT" "12.834519,15.643883,-0.110165")
(COMMAND "POINT" "12.947729,15.675803,-0.116856")
(COMMAND "POINT" "13.059552,15.709626,-0.121541")
(COMMAND "POINT" "13.169986,15.745352,-0.124221")
(COMMAND "POINT" "13.279033,15.782981,-0.124897")
(COMMAND "POINT" "13.386692,15.822513,-0.123567")
(COMMAND "POINT" "13.492963,15.863948,-0.120232")
(COMMAND "POINT" "13.597847,15.907285,-0.114893")
(COMMAND "POINT" "13.701343,15.952526,-0.107549")
(COMMAND "POINT" "13.803451,15.999670,-0.098199")
(COMMAND "POINT" "13.904171,16.048716,-0.086845")
(COMMAND "POINT" "14.003504,16.099666,-0.073486")
(COMMAND "POINT" "14.101448,16.152518,-0.058122")
(COMMAND "POINT" "14.198005,16.207274,-0.040753")
(COMMAND "POINT" "14.293175,16.263932,-0.021379")
(COMMAND "POINT" "14.386956,16.322494,0.000000")
(COMMAND "POINT" "3.104016,15.216186,1.695276")
(COMMAND "POINT" "3.138094,15.280315,1.761426")
(COMMAND "POINT" "3.174828,15.342351,1.824601")
(COMMAND "POINT" "3.214216,15.402293,1.884799")
(COMMAND "POINT" "3.256259,15.460143,1.942022")
(COMMAND "POINT" "3.300956,15.515899,1.996269")
(COMMAND "POINT" "3.348308,15.569562,2.047540")
(COMMAND "POINT" "3.398315,15.621132,2.095836")
(COMMAND "POINT" "3.450977,15.670608,2.141155")
(COMMAND "POINT" "3.506293,15.717991,2.183499")
(COMMAND "POINT" "3.564264,15.763281,2.222866")
(COMMAND "POINT" "3.624890,15.806478,2.259258")
(COMMAND "POINT" "3.688171,15.847582,2.292674")
(COMMAND "POINT" "3.754106,15.886592,2.323114")
(COMMAND "POINT" "3.822696,15.923510,2.350579")
(COMMAND "POINT" "3.893941,15.958334,2.375067")
(COMMAND "POINT" "3.967841,15.991065,2.396580")
(COMMAND "POINT" "4.044395,16.021702,2.415117")
(COMMAND "POINT" "4.123604,16.050247,2.430678")
(COMMAND "POINT" "4.205467,16.076698,2.443263")
(COMMAND "POINT" "4.289986,16.101056,2.452872")
(COMMAND "POINT" "4.377159,16.123321,2.459506")
(COMMAND "POINT" "4.466987,16.143492,2.463163")
(COMMAND "POINT" "4.559469,16.161571,2.463845")
(COMMAND "POINT" "4.654607,16.177556,2.461551")
(COMMAND "POINT" "4.752399,16.191448,2.456281")
(COMMAND "POINT" "4.852845,16.203247,2.448036")
(COMMAND "POINT" "4.955947,16.212952,2.436814")
(COMMAND "POINT" "5.061703,16.220564,2.422617")
(COMMAND "POINT" "5.170114,16.226084,2.405443")
(COMMAND "POINT" "5.281180,16.229510,2.385294")
(COMMAND "POINT" "5.394900,16.230842,2.362169")
(COMMAND "POINT" "5.511275,16.230082,2.336069")
(COMMAND "POINT" "5.630305,16.227228,2.306992")
(COMMAND "POINT" "5.751990,16.222281,2.274940")
(COMMAND "POINT" "5.876329,16.215241,2.239911")
(COMMAND "POINT" "6.003323,16.206108,2.201907")
(COMMAND "POINT" "6.132972,16.194881,2.160927")
(COMMAND "POINT" "6.265275,16.181561,2.116971")
(COMMAND "POINT" "6.400233,16.166148,2.070040")
(COMMAND "POINT" "6.537846,16.148642,2.020132")
(COMMAND "POINT" "6.678114,16.129043,1.967249")
(COMMAND "POINT" "6.821036,16.107350,1.911390")
(COMMAND "POINT" "6.966613,16.083565,1.852555")
(COMMAND "POINT" "7.114845,16.057686,1.790744")
(COMMAND "POINT" "7.265732,16.029713,1.725957")
(COMMAND "POINT" "7.419273,15.999648,1.658195")
(COMMAND "POINT" "7.575469,15.967489,1.587456")
(COMMAND "POINT" "7.734320,15.933238,1.513742")
(COMMAND "POINT" "7.895825,15.896893,1.437052")
(COMMAND "POINT" "8.059474,15.858956,1.358018")
(COMMAND "POINT" "8.222201,15.822440,1.280430")
(COMMAND "POINT" "8.383493,15.787847,1.204920")
(COMMAND "POINT" "8.543351,15.755176,1.131489")
(COMMAND "POINT" "8.701775,15.724427,1.060135")
(COMMAND "POINT" "8.858765,15.695600,0.990859")
(COMMAND "POINT" "9.014321,15.668696,0.923662")
(COMMAND "POINT" "9.168443,15.643715,0.858542")
(COMMAND "POINT" "9.321131,15.620655,0.795501")
(COMMAND "POINT" "9.472385,15.599518,0.734537")
(COMMAND "POINT" "9.622204,15.580304,0.675652")
(COMMAND "POINT" "9.770590,15.563011,0.618845")
(COMMAND "POINT" "9.917542,15.547641,0.564115")
(COMMAND "POINT" "10.063060,15.534194,0.511464")
(COMMAND "POINT" "10.207144,15.522668,0.460891")
(COMMAND "POINT" "10.349793,15.513066,0.412396")
(COMMAND "POINT" "10.491009,15.505385,0.365979")
(COMMAND "POINT" "10.630791,15.499627,0.321640")
(COMMAND "POINT" "10.769138,15.495791,0.279379")
(COMMAND "POINT" "10.906052,15.493878,0.239196")
(COMMAND "POINT" "11.041531,15.493887,0.201091")
(COMMAND "POINT" "11.175577,15.495818,0.165064")
(COMMAND "POINT" "11.308188,15.499672,0.131115")
(COMMAND "POINT" "11.439366,15.505448,0.099244")
(COMMAND "POINT" "11.569109,15.513146,0.069452")
(COMMAND "POINT" "11.697418,15.522767,0.041737")
(COMMAND "POINT" "11.824294,15.534310,0.016100")
(COMMAND "POINT" "11.949735,15.547775,-0.007458")
(COMMAND "POINT" "12.073742,15.563163,-0.028939")
(COMMAND "POINT" "12.196316,15.580473,-0.048341")
(COMMAND "POINT" "12.317455,15.599706,-0.065666")
(COMMAND "POINT" "12.437160,15.620861,-0.080912")
(COMMAND "POINT" "12.555431,15.643938,-0.094080")
(COMMAND "POINT" "12.672268,15.668937,-0.105170")
(COMMAND "POINT" "12.787671,15.695859,-0.114183")
(COMMAND "POINT" "12.901640,15.724704,-0.121117")
(COMMAND "POINT" "13.014175,15.755470,-0.125973")
(COMMAND "POINT" "13.125276,15.788159,-0.128751")
(COMMAND "POINT" "13.234943,15.822771,-0.129451")
(COMMAND "POINT" "13.343176,15.859305,-0.128073")
(COMMAND "POINT" "13.449975,15.897761,-0.124617")
(COMMAND "POINT" "13.555340,15.938139,-0.119083")
(COMMAND "POINT" "13.659271,15.980440,-0.111471")
(COMMAND "POINT" "13.761768,16.024663,-0.101780")
(COMMAND "POINT" "13.862830,16.070809,-0.090012")
(COMMAND "POINT" "13.962459,16.118877,-0.076166")
(COMMAND "POINT" "14.060654,16.168867,-0.060241")
(COMMAND "POINT" "14.157414,16.220779,-0.042239")
(COMMAND "POINT" "14.252741,16.274614,-0.022159")
(COMMAND "POINT" "14.346634,16.330372,0.000000")
(COMMAND "POINT" "3.042729,15.288720,1.755676")
(COMMAND "POINT" "3.072752,15.360388,1.824183")
(COMMAND "POINT" "3.105560,15.429730,1.889608")
(COMMAND "POINT" "3.141154,15.496747,1.951951")
(COMMAND "POINT" "3.179533,15.561439,2.011213")
(COMMAND "POINT" "3.220697,15.623805,2.067393")
(COMMAND "POINT" "3.264646,15.683846,2.120490")
(COMMAND "POINT" "3.311381,15.741562,2.170506")
(COMMAND "POINT" "3.360901,15.796952,2.217440")
(COMMAND "POINT" "3.413206,15.850017,2.261293")
(COMMAND "POINT" "3.468297,15.900757,2.302063")
(COMMAND "POINT" "3.526172,15.949171,2.339751")
(COMMAND "POINT" "3.586833,15.995260,2.374358")
(COMMAND "POINT" "3.650279,16.039023,2.405883")
(COMMAND "POINT" "3.716511,16.080462,2.434326")
(COMMAND "POINT" "3.785528,16.119574,2.459687")
(COMMAND "POINT" "3.857330,16.156362,2.481966")
(COMMAND "POINT" "3.931917,16.190824,2.501163")
(COMMAND "POINT" "4.009290,16.222961,2.517278")
(COMMAND "POINT" "4.089448,16.252772,2.530312")
(COMMAND "POINT" "4.172391,16.280258,2.540264")
(COMMAND "POINT" "4.258119,16.305419,2.547134")
(COMMAND "POINT" "4.346633,16.328254,2.550921")
(COMMAND "POINT" "4.437932,16.348764,2.551628")
(COMMAND "POINT" "4.532016,16.366949,2.549252")
(COMMAND "POINT" "4.628885,16.382808,2.543794")
(COMMAND "POINT" "4.728540,16.396342,2.535255")
(COMMAND "POINT" "4.830980,16.407550,2.523633")
(COMMAND "POINT" "4.936205,16.416434,2.508930")
(COMMAND "POINT" "5.044216,16.422991,2.491145")
(COMMAND "POINT" "5.155011,16.427224,2.470278")
(COMMAND "POINT" "5.268593,16.429131,2.446329")
(COMMAND "POINT" "5.384959,16.428713,2.419299")
(COMMAND "POINT" "5.504110,16.425969,2.389186")
(COMMAND "POINT" "5.626047,16.420900,2.355992")
(COMMAND "POINT" "5.750769,16.413506,2.319715")
(COMMAND "POINT" "5.878277,16.403786,2.280357")
(COMMAND "POINT" "6.008569,16.391741,2.237917")
(COMMAND "POINT" "6.141647,16.377371,2.192395")
(COMMAND "POINT" "6.277511,16.360675,2.143792")
(COMMAND "POINT" "6.416159,16.341654,2.092106")
(COMMAND "POINT" "6.557593,16.320308,2.037339")
(COMMAND "POINT" "6.701812,16.296636,1.979489")
(COMMAND "POINT" "6.848816,16.270639,1.918558")
(COMMAND "POINT" "6.998605,16.242316,1.854545")
(COMMAND "POINT" "7.151180,16.211668,1.787450")
(COMMAND "POINT" "7.306540,16.178695,1.717273")
(COMMAND "POINT" "7.464686,16.143396,1.644015")
(COMMAND "POINT" "7.625616,16.105773,1.567674")
(COMMAND "POINT" "7.789332,16.065823,1.488252")
(COMMAND "POINT" "7.955300,16.024082,1.406402")
(COMMAND "POINT" "8.120317,15.983749,1.326050")
(COMMAND "POINT" "8.283852,15.945356,1.247850")
(COMMAND "POINT" "8.445904,15.908905,1.171802")
(COMMAND "POINT" "8.606472,15.874396,1.097906")
(COMMAND "POINT" "8.765557,15.841827,1.026162")
(COMMAND "POINT" "8.923159,15.811200,0.956570")
(COMMAND "POINT" "9.079278,15.782514,0.889131")
(COMMAND "POINT" "9.233913,15.755769,0.823843")
(COMMAND "POINT" "9.387065,15.730965,0.760708")
(COMMAND "POINT" "9.538734,15.708103,0.699724")
(COMMAND "POINT" "9.688920,15.687182,0.640893")
(COMMAND "POINT" "9.837623,15.668202,0.584214")
(COMMAND "POINT" "9.984842,15.651163,0.529687")
(COMMAND "POINT" "10.130579,15.636066,0.477312")
(COMMAND "POINT" "10.274832,15.622909,0.427089")
(COMMAND "POINT" "10.417601,15.611694,0.379018")
(COMMAND "POINT" "10.558888,15.602421,0.333099")
(COMMAND "POINT" "10.698691,15.595088,0.289332")
(COMMAND "POINT" "10.837012,15.589697,0.247718")
(COMMAND "POINT" "10.973849,15.586247,0.208255")
(COMMAND "POINT" "11.109202,15.584738,0.170945")
(COMMAND "POINT" "11.243073,15.585170,0.135786")
(COMMAND "POINT" "11.375460,15.587544,0.102780")
(COMMAND "POINT" "11.506365,15.591858,0.071926")
(COMMAND "POINT" "11.635786,15.598114,0.043224")
(COMMAND "POINT" "11.763723,15.606312,0.016674")
(COMMAND "POINT" "11.890178,15.616450,-0.007724")
(COMMAND "POINT" "12.015149,15.628530,-0.029970")
(COMMAND "POINT" "12.138637,15.642551,-0.050063")
(COMMAND "POINT" "12.260642,15.658513,-0.068005")
(COMMAND "POINT" "12.381164,15.676416,-0.083795")
(COMMAND "POINT" "12.500203,15.696261,-0.097432")
(COMMAND "POINT" "12.617758,15.718047,-0.108918")
(COMMAND "POINT" "12.733830,15.741774,-0.118251")
(COMMAND "POINT" "12.848419,15.767442,-0.125432")
(COMMAND "POINT" "12.961525,15.795051,-0.130461")
(COMMAND "POINT" "13.073147,15.824602,-0.133338")
(COMMAND "POINT" "13.183287,15.856094,-0.134063")
(COMMAND "POINT" "13.291943,15.889527,-0.132636")
(COMMAND "POINT" "13.399116,15.924902,-0.129057")
(COMMAND "POINT" "13.504805,15.962217,-0.123326")
(COMMAND "POINT" "13.609012,16.001474,-0.115442")
(COMMAND "POINT" "13.711735,16.042672,-0.105407")
(COMMAND "POINT" "13.812975,16.085812,-0.093219")
(COMMAND "POINT" "13.912732,16.130892,-0.078879")
(COMMAND "POINT" "14.011006,16.177914,-0.062388")
(COMMAND "POINT" "14.107796,16.226877,-0.043744")
(COMMAND "POINT" "14.203103,16.277781,-0.022948")
(COMMAND "POINT" "14.296927,16.330627,0.000000")
(COMMAND "POINT" "2.982844,15.360554,1.816829")
(COMMAND "POINT" "3.008635,15.439751,1.887723")
(COMMAND "POINT" "3.037344,15.516388,1.955427")
(COMMAND "POINT" "3.068971,15.590467,2.019942")
(COMMAND "POINT" "3.103518,15.661986,2.081267")
(COMMAND "POINT" "3.140983,15.730947,2.139404")
(COMMAND "POINT" "3.181366,15.797349,2.194351")
(COMMAND "POINT" "3.224669,15.861192,2.246109")
(COMMAND "POINT" "3.270889,15.922476,2.294678")
(COMMAND "POINT" "3.320029,15.981201,2.340058")
(COMMAND "POINT" "3.372087,16.037367,2.382248")
(COMMAND "POINT" "3.427064,16.090974,2.421249")
(COMMAND "POINT" "3.484959,16.142022,2.457061")
(COMMAND "POINT" "3.545773,16.190511,2.489684")
(COMMAND "POINT" "3.609506,16.236441,2.519118")
(COMMAND "POINT" "3.676158,16.279812,2.545362")
(COMMAND "POINT" "3.745728,16.320624,2.568417")
(COMMAND "POINT" "3.818216,16.358878,2.588283")
(COMMAND "POINT" "3.893624,16.394572,2.604960")
(COMMAND "POINT" "3.971950,16.427707,2.618447")
(COMMAND "POINT" "4.053194,16.458284,2.628746")
(COMMAND "POINT" "4.137357,16.486301,2.635855")
(COMMAND "POINT" "4.224439,16.511760,2.639775")
(COMMAND "POINT" "4.314440,16.534659,2.640505")
(COMMAND "POINT" "4.407359,16.555000,2.638047")
(COMMAND "POINT" "4.503197,16.572782,2.632399")
(COMMAND "POINT" "4.601953,16.588004,2.623562")
(COMMAND "POINT" "4.703628,16.600668,2.611536")
(COMMAND "POINT" "4.808222,16.610773,2.596321")
(COMMAND "POINT" "4.915735,16.618319,2.577916")
(COMMAND "POINT" "5.026166,16.623306,2.556322")
(COMMAND "POINT" "5.139515,16.625734,2.531539")
(COMMAND "POINT" "5.255784,16.625603,2.503567")
(COMMAND "POINT" "5.374971,16.622913,2.472406")
(COMMAND "POINT" "5.497076,16.617664,2.438055")
(COMMAND "POINT" "5.622101,16.609856,2.400515")
(COMMAND "POINT" "5.750043,16.599489,2.359786")
(COMMAND "POINT" "5.880905,16.586563,2.315868")
(COMMAND "POINT" "6.014685,16.571079,2.268761")
(COMMAND "POINT" "6.151384,16.553035,2.218464")
(COMMAND "POINT" "6.291001,16.532432,2.164978")
(COMMAND "POINT" "6.433538,16.509271,2.108303")
(COMMAND "POINT" "6.578992,16.483550,2.048439")
(COMMAND "POINT" "6.727366,16.455271,1.985385")
(COMMAND "POINT" "6.878658,16.424432,1.919142")
(COMMAND "POINT" "7.032869,16.391035,1.849710")
(COMMAND "POINT" "7.189998,16.355079,1.777089")
(COMMAND "POINT" "7.350046,16.316563,1.701279")
(COMMAND "POINT" "7.513012,16.275489,1.622279")
(COMMAND "POINT" "7.678898,16.231856,1.540090")
(COMMAND "POINT" "7.847145,16.186229,1.455389")
(COMMAND "POINT" "8.014414,16.141996,1.372238")
(COMMAND "POINT" "8.180147,16.099723,1.291315")
(COMMAND "POINT" "8.344345,16.059409,1.212618")
(COMMAND "POINT" "8.507008,16.021055,1.136148")
(COMMAND "POINT" "8.668135,15.984661,1.061905")
(COMMAND "POINT" "8.827728,15.950226,0.989889")
(COMMAND "POINT" "8.985785,15.917751,0.920101")
(COMMAND "POINT" "9.142307,15.887235,0.852539")
(COMMAND "POINT" "9.297293,15.858679,0.787204")
(COMMAND "POINT" "9.450744,15.832082,0.724097")
(COMMAND "POINT" "9.602660,15.807445,0.663216")
(COMMAND "POINT" "9.753041,15.784767,0.604563")
(COMMAND "POINT" "9.901887,15.764049,0.548137")
(COMMAND "POINT" "10.049197,15.745291,0.493937")
(COMMAND "POINT" "10.194972,15.728492,0.441965")
(COMMAND "POINT" "10.339211,15.713653,0.392220")
(COMMAND "POINT" "10.481916,15.700773,0.344701")
(COMMAND "POINT" "10.623085,15.689852,0.299410")
(COMMAND "POINT" "10.762719,15.680892,0.256346")
(COMMAND "POINT" "10.900818,15.673890,0.215509")
(COMMAND "POINT" "11.037381,15.668849,0.176899")
(COMMAND "POINT" "11.172409,15.665767,0.140516")
(COMMAND "POINT" "11.305902,15.664644,0.106360")
(COMMAND "POINT" "11.437859,15.665481,0.074431")
(COMMAND "POINT" "11.568282,15.668278,0.044730")
(COMMAND "POINT" "11.697169,15.673034,0.017255")
(COMMAND "POINT" "11.824521,15.679749,-0.007993")
(COMMAND "POINT" "11.950337,15.688424,-0.031014")
(COMMAND "POINT" "12.074618,15.699059,-0.051807")
(COMMAND "POINT" "12.197364,15.711653,-0.070374")
(COMMAND "POINT" "12.318575,15.726207,-0.086713")
(COMMAND "POINT" "12.438250,15.742721,-0.100826")
(COMMAND "POINT" "12.556391,15.761193,-0.112711")
(COMMAND "POINT" "12.672995,15.781626,-0.122370")
(COMMAND "POINT" "12.788065,15.804018,-0.129801")
(COMMAND "POINT" "12.901600,15.828369,-0.135005")
(COMMAND "POINT" "13.013599,15.854680,-0.137983")
(COMMAND "POINT" "13.124063,15.882951,-0.138733")
(COMMAND "POINT" "13.232991,15.913181,-0.137256")
(COMMAND "POINT" "13.340384,15.945371,-0.133552")
(COMMAND "POINT" "13.446242,15.979520,-0.127621")
(COMMAND "POINT" "13.550565,16.015629,-0.119463")
(COMMAND "POINT" "13.653353,16.053697,-0.109078")
(COMMAND "POINT" "13.754605,16.093725,-0.096466")
(COMMAND "POINT" "13.854322,16.135713,-0.081627")
(COMMAND "POINT" "13.952504,16.179660,-0.064561")
(COMMAND "POINT" "14.049150,16.225566,-0.045268")
(COMMAND "POINT" "14.144262,16.273432,-0.023747")
(COMMAND "POINT" "14.237837,16.323258,0.000000")
(COMMAND "POINT" "2.924362,15.431688,1.878736")
(COMMAND "POINT" "2.945742,15.518404,1.952045")
(COMMAND "POINT" "2.970178,15.602325,2.022057")
(COMMAND "POINT" "2.997668,15.683452,2.088770")
(COMMAND "POINT" "3.028213,15.761785,2.152185")
(COMMAND "POINT" "3.061813,15.837325,2.212303")
(COMMAND "POINT" "3.098468,15.910070,2.269122")
(COMMAND "POINT" "3.138178,15.980021,2.322644")
(COMMAND "POINT" "3.180942,16.047178,2.372868")
(COMMAND "POINT" "3.226762,16.111541,2.419794")
(COMMAND "POINT" "3.275636,16.173111,2.463422")
(COMMAND "POINT" "3.327565,16.231886,2.503752")
(COMMAND "POINT" "3.382549,16.287867,2.540784")
(COMMAND "POINT" "3.440588,16.341054,2.574518")
(COMMAND "POINT" "3.501682,16.391447,2.604955")
(COMMAND "POINT" "3.565831,16.439047,2.632094")
(COMMAND "POINT" "3.633034,16.483852,2.655934")
(COMMAND "POINT" "3.703292,16.525863,2.676477")
(COMMAND "POINT" "3.776605,16.565080,2.693722")
(COMMAND "POINT" "3.852974,16.601504,2.707669")
(COMMAND "POINT" "3.932396,16.635133,2.718319")
(COMMAND "POINT" "4.014874,16.665968,2.725670")
(COMMAND "POINT" "4.100407,16.694009,2.729723")
(COMMAND "POINT" "4.188994,16.719256,2.730479")
(COMMAND "POINT" "4.280636,16.741710,2.727937")
(COMMAND "POINT" "4.375334,16.761369,2.722097")
(COMMAND "POINT" "4.473086,16.778234,2.712958")
(COMMAND "POINT" "4.573893,16.792305,2.700523")
(COMMAND "POINT" "4.677754,16.803583,2.684789")
(COMMAND "POINT" "4.784671,16.812066,2.665757")
(COMMAND "POINT" "4.894642,16.817755,2.643427")
(COMMAND "POINT" "5.007669,16.820650,2.617800")
(COMMAND "POINT" "5.123750,16.820751,2.588875")
(COMMAND "POINT" "5.242886,16.818059,2.556651")
(COMMAND "POINT" "5.365077,16.812572,2.521130")
(COMMAND "POINT" "5.490322,16.804291,2.482311")
(COMMAND "POINT" "5.618623,16.793216,2.440194")
(COMMAND "POINT" "5.749978,16.779348,2.394780")
(COMMAND "POINT" "5.884389,16.762685,2.346067")
(COMMAND "POINT" "6.021854,16.743228,2.294057")
(COMMAND "POINT" "6.162374,16.720977,2.238748")
(COMMAND "POINT" "6.305949,16.695933,2.180142")
(COMMAND "POINT" "6.452578,16.668094,2.118238")
(COMMAND "POINT" "6.602263,16.637461,2.053036")
(COMMAND "POINT" "6.755002,16.604034,1.984536")
(COMMAND "POINT" "6.910797,16.567813,1.912738")
(COMMAND "POINT" "7.069646,16.528799,1.837642")
(COMMAND "POINT" "7.231550,16.486990,1.759249")
(COMMAND "POINT" "7.396509,16.442387,1.677557")
(COMMAND "POINT" "7.564523,16.394990,1.592568")
(COMMAND "POINT" "7.735010,16.345396,1.504981")
(COMMAND "POINT" "7.904489,16.297183,1.418997")
(COMMAND "POINT" "8.072377,16.250947,1.335315")
(COMMAND "POINT" "8.238675,16.206688,1.253937")
(COMMAND "POINT" "8.403383,16.164406,1.174861")
(COMMAND "POINT" "8.566500,16.124102,1.098089")
(COMMAND "POINT" "8.728028,16.085775,1.023619")
(COMMAND "POINT" "8.887965,16.049426,0.951452")
(COMMAND "POINT" "9.046312,16.015054,0.881589")
(COMMAND "POINT" "9.203068,15.982659,0.814028")
(COMMAND "POINT" "9.358235,15.952241,0.748770")
(COMMAND "POINT" "9.511811,15.923801,0.685815")
(COMMAND "POINT" "9.663797,15.897338,0.625163")
(COMMAND "POINT" "9.814193,15.872852,0.566814")
(COMMAND "POINT" "9.962999,15.850344,0.510768")
(COMMAND "POINT" "10.110214,15.829813,0.457025")
(COMMAND "POINT" "10.255839,15.811260,0.405584")
(COMMAND "POINT" "10.399874,15.794683,0.356447")
(COMMAND "POINT" "10.542319,15.780084,0.309613")
(COMMAND "POINT" "10.683174,15.767463,0.265081")
(COMMAND "POINT" "10.822438,15.756818,0.222852")
(COMMAND "POINT" "10.960112,15.748151,0.182927")
(COMMAND "POINT" "11.096196,15.741461,0.145304")
(COMMAND "POINT" "11.230690,15.736749,0.109984")
(COMMAND "POINT" "11.363594,15.734014,0.076968")
(COMMAND "POINT" "11.494907,15.733256,0.046254")
(COMMAND "POINT" "11.624630,15.734476,0.017843")
(COMMAND "POINT" "11.752763,15.737673,-0.008265")
(COMMAND "POINT" "11.879306,15.742847,-0.032070")
(COMMAND "POINT" "12.004258,15.749998,-0.053573")
(COMMAND "POINT" "12.127620,15.759127,-0.072772")
(COMMAND "POINT" "12.249393,15.770233,-0.089668")
(COMMAND "POINT" "12.369574,15.783317,-0.104261")
(COMMAND "POINT" "12.488166,15.798378,-0.116552")
(COMMAND "POINT" "12.605168,15.815416,-0.126539")
(COMMAND "POINT" "12.720579,15.834431,-0.134224")
(COMMAND "POINT" "12.834400,15.855424,-0.139606")
(COMMAND "POINT" "12.946631,15.878394,-0.142684")
(COMMAND "POINT" "13.057271,15.903342,-0.143460")
(COMMAND "POINT" "13.166322,15.930266,-0.141933")
(COMMAND "POINT" "13.273782,15.959168,-0.138103")
(COMMAND "POINT" "13.379652,15.990048,-0.131970")
(COMMAND "POINT" "13.483932,16.022904,-0.123534")
(COMMAND "POINT" "13.586621,16.057738,-0.112795")
(COMMAND "POINT" "13.687721,16.094550,-0.099753")
(COMMAND "POINT" "13.787230,16.133338,-0.084408")
(COMMAND "POINT" "13.885149,16.174104,-0.066761")
(COMMAND "POINT" "13.981477,16.216848,-0.046810")
(COMMAND "POINT" "14.076216,16.261568,-0.024556")
(COMMAND "POINT" "14.169364,16.308266,0.000000")
(COMMAND "POINT" "2.867281,15.502123,1.941398")
(COMMAND "POINT" "2.884075,15.596347,2.017152")
(COMMAND "POINT" "2.904062,15.687540,2.089498")
(COMMAND "POINT" "2.927244,15.775703,2.158436")
(COMMAND "POINT" "2.953619,15.860836,2.223966")
(COMMAND "POINT" "2.983189,15.942937,2.286089")
(COMMAND "POINT" "3.015952,16.022009,2.344804")
(COMMAND "POINT" "3.051909,16.098050,2.400110")
(COMMAND "POINT" "3.091060,16.171060,2.452009")
(COMMAND "POINT" "3.133405,16.241040,2.500500")
(COMMAND "POINT" "3.178944,16.307989,2.545584")
(COMMAND "POINT" "3.227677,16.371908,2.587259")
(COMMAND "POINT" "3.279603,16.432796,2.625526")
(COMMAND "POINT" "3.334724,16.490654,2.660386")
(COMMAND "POINT" "3.393038,16.545481,2.691837")
(COMMAND "POINT" "3.454547,16.597278,2.719881")
(COMMAND "POINT" "3.519249,16.646045,2.744517")
(COMMAND "POINT" "3.587145,16.691781,2.765745")
(COMMAND "POINT" "3.658235,16.734486,2.783565")
(COMMAND "POINT" "3.732519,16.774161,2.797978")
(COMMAND "POINT" "3.809997,16.810805,2.808982")
(COMMAND "POINT" "3.890669,16.844419,2.816579")
(COMMAND "POINT" "3.974535,16.875002,2.820767")
(COMMAND "POINT" "4.061594,16.902555,2.821548")
(COMMAND "POINT" "4.151848,16.927078,2.818921")
(COMMAND "POINT" "4.245295,16.948570,2.812886")
(COMMAND "POINT" "4.341937,16.967031,2.803443")
(COMMAND "POINT" "4.441772,16.982462,2.790593")
(COMMAND "POINT" "4.544801,16.994862,2.774334")
(COMMAND "POINT" "4.651024,17.004232,2.754667")
(COMMAND "POINT" "4.760441,17.010572,2.731593")
(COMMAND "POINT" "4.873052,17.013881,2.705111")
(COMMAND "POINT" "4.988857,17.014159,2.675221")
(COMMAND "POINT" "5.107856,17.011407,2.641923")
(COMMAND "POINT" "5.230048,17.005625,2.605217")
(COMMAND "POINT" "5.355435,16.996811,2.565103")
(COMMAND "POINT" "5.484015,16.984968,2.521582")
(COMMAND "POINT" "5.615790,16.970094,2.474652")
(COMMAND "POINT" "5.750758,16.952189,2.424315")
(COMMAND "POINT" "5.888920,16.931254,2.370570")
(COMMAND "POINT" "6.030276,16.907289,2.313417")
(COMMAND "POINT" "6.174826,16.880293,2.252856")
(COMMAND "POINT" "6.322570,16.850266,2.188887")
(COMMAND "POINT" "6.473508,16.817209,2.121510")
(COMMAND "POINT" "6.627639,16.781122,2.050726")
(COMMAND "POINT" "6.784965,16.742004,1.976533")
(COMMAND "POINT" "6.945484,16.699855,1.898933")
(COMMAND "POINT" "7.109198,16.654676,1.817925")
(COMMAND "POINT" "7.276105,16.606467,1.733508")
(COMMAND "POINT" "7.446206,16.555227,1.645685")
(COMMAND "POINT" "7.618896,16.501585,1.555176")
(COMMAND "POINT" "7.790543,16.449309,1.466324")
(COMMAND "POINT" "7.960542,16.399027,1.379852")
(COMMAND "POINT" "8.128893,16.350740,1.295759")
(COMMAND "POINT" "8.295596,16.304448,1.214046")
(COMMAND "POINT" "8.460651,16.260150,1.134713")
(COMMAND "POINT" "8.624058,16.217847,1.057760")
(COMMAND "POINT" "8.785817,16.177539,0.983186")
(COMMAND "POINT" "8.945928,16.139224,0.910992")
(COMMAND "POINT" "9.104391,16.102905,0.841178")
(COMMAND "POINT" "9.261205,16.068580,0.773744")
(COMMAND "POINT" "9.416372,16.036249,0.708689")
(COMMAND "POINT" "9.569891,16.005913,0.646014")
(COMMAND "POINT" "9.721761,15.977572,0.585719")
(COMMAND "POINT" "9.871984,15.951225,0.527803")
(COMMAND "POINT" "10.020558,15.926873,0.472268")
(COMMAND "POINT" "10.167485,15.904515,0.419112")
(COMMAND "POINT" "10.312763,15.884152,0.368335")
(COMMAND "POINT" "10.456394,15.865783,0.319939")
(COMMAND "POINT" "10.598376,15.849409,0.273922")
(COMMAND "POINT" "10.738710,15.835030,0.230285")
(COMMAND "POINT" "10.877396,15.822645,0.189028")
(COMMAND "POINT" "11.014435,15.812254,0.150150")
(COMMAND "POINT" "11.149825,15.803859,0.113653")
(COMMAND "POINT" "11.283567,15.797457,0.079535")
(COMMAND "POINT" "11.415661,15.793050,0.047796")
(COMMAND "POINT" "11.546107,15.790638,0.018438")
(COMMAND "POINT" "11.674905,15.790220,-0.008541")
(COMMAND "POINT" "11.802055,15.791797,-0.033140")
(COMMAND "POINT" "11.927557,15.795369,-0.055359")
(COMMAND "POINT" "12.051411,15.800935,-0.075199")
(COMMAND "POINT" "12.173617,15.808495,-0.092659")
(COMMAND "POINT" "12.294175,15.818050,-0.107739")
(COMMAND "POINT" "12.413084,15.829600,-0.120439")
(COMMAND "POINT" "12.530346,15.843144,-0.130760")
(COMMAND "POINT" "12.645960,15.858682,-0.138701")
(COMMAND "POINT" "12.759926,15.876216,-0.144262")
(COMMAND "POINT" "12.872243,15.895743,-0.147443")
(COMMAND "POINT" "12.982913,15.917266,-0.148245")
(COMMAND "POINT" "13.091934,15.940782,-0.146667")
(COMMAND "POINT" "13.199308,15.966294,-0.142709")
(COMMAND "POINT" "13.305033,15.993800,-0.136371")
(COMMAND "POINT" "13.409111,16.023300,-0.127654")
(COMMAND "POINT" "13.511540,16.054795,-0.116557")
(COMMAND "POINT" "13.612321,16.088285,-0.103080")
(COMMAND "POINT" "13.711455,16.123769,-0.087224")
(COMMAND "POINT" "13.808940,16.161248,-0.068987")
(COMMAND "POINT" "13.904777,16.200721,-0.048371")
(COMMAND "POINT" "13.998966,16.242189,-0.025376")
(COMMAND "POINT" "14.091507,16.285651,0.000000")
(COMMAND "POINT" "2.811603,15.571859,2.004813")
(COMMAND "POINT" "2.823632,15.673581,2.083041")
(COMMAND "POINT" "2.838998,15.772035,2.157750")
(COMMAND "POINT" "2.857699,15.867220,2.228940")
(COMMAND "POINT" "2.879736,15.959137,2.296611")
(COMMAND "POINT" "2.905109,16.047786,2.360763")
(COMMAND "POINT" "2.933818,16.133166,2.421396")
(COMMAND "POINT" "2.965862,16.215277,2.478509")
(COMMAND "POINT" "3.001242,16.294121,2.532103")
(COMMAND "POINT" "3.039958,16.369695,2.582178")
(COMMAND "POINT" "3.082010,16.442002,2.628734")
(COMMAND "POINT" "3.127398,16.511040,2.671771")
(COMMAND "POINT" "3.176121,16.576809,2.711288")
(COMMAND "POINT" "3.228180,16.639310,2.747286")
(COMMAND "POINT" "3.283575,16.698543,2.779765")
(COMMAND "POINT" "3.342306,16.754507,2.808725")
(COMMAND "POINT" "3.404373,16.807203,2.834166")
(COMMAND "POINT" "3.469775,16.856630,2.856087")
(COMMAND "POINT" "3.538513,16.902789,2.874489")
(COMMAND "POINT" "3.610587,16.945679,2.889372")
(COMMAND "POINT" "3.685997,16.985301,2.900736")
(COMMAND "POINT" "3.764742,17.021654,2.908581")
(COMMAND "POINT" "3.846824,17.054739,2.912906")
(COMMAND "POINT" "3.932241,17.084556,2.913713")
(COMMAND "POINT" "4.020994,17.111104,2.911000")
(COMMAND "POINT" "4.113082,17.134384,2.904768")
(COMMAND "POINT" "4.208507,17.154395,2.895017")
(COMMAND "POINT" "4.307267,17.171138,2.881746")
(COMMAND "POINT" "4.409363,17.184612,2.864956")
(COMMAND "POINT" "4.514795,17.194818,2.844648")
(COMMAND "POINT" "4.623563,17.201756,2.820819")
(COMMAND "POINT" "4.735666,17.205425,2.793472")
(COMMAND "POINT" "4.851105,17.205826,2.762606")
(COMMAND "POINT" "4.969880,17.202958,2.728220")
(COMMAND "POINT" "5.091991,17.196822,2.690315")
(COMMAND "POINT" "5.217438,17.187417,2.648891")
(COMMAND "POINT" "5.346220,17.174744,2.603948")
(COMMAND "POINT" "5.478339,17.158802,2.555486")
(COMMAND "POINT" "5.613793,17.139592,2.503504")
(COMMAND "POINT" "5.752582,17.117114,2.448003")
(COMMAND "POINT" "5.894708,17.091367,2.388983")
(COMMAND "POINT" "6.040169,17.062352,2.326444")
(COMMAND "POINT" "6.188967,17.030068,2.260386")
(COMMAND "POINT" "6.341100,16.994516,2.190808")
(COMMAND "POINT" "6.496568,16.955695,2.117712")
(COMMAND "POINT" "6.655373,16.913606,2.041096")
(COMMAND "POINT" "6.817513,16.868248,1.960961")
(COMMAND "POINT" "6.982990,16.819622,1.877306")
(COMMAND "POINT" "7.151802,16.767728,1.790133")
(COMMAND "POINT" "7.323949,16.712565,1.699440")
(COMMAND "POINT" "7.498802,16.654794,1.605975")
(COMMAND "POINT" "7.672577,16.598374,1.514221")
(COMMAND "POINT" "7.844643,16.543965,1.424924")
(COMMAND "POINT" "8.015000,16.491567,1.338085")
(COMMAND "POINT" "8.183649,16.441181,1.253703")
(COMMAND "POINT" "8.350589,16.392806,1.171778")
(COMMAND "POINT" "8.515820,16.346442,1.092311")
(COMMAND "POINT" "8.679342,16.302089,1.015301")
(COMMAND "POINT" "8.841155,16.259748,0.940749")
(COMMAND "POINT" "9.001260,16.219417,0.868655")
(COMMAND "POINT" "9.159656,16.181098,0.799018")
(COMMAND "POINT" "9.316343,16.144791,0.731838")
(COMMAND "POINT" "9.471322,16.110494,0.667116")
(COMMAND "POINT" "9.624591,16.078209,0.604851")
(COMMAND "POINT" "9.776152,16.047935,0.545044")
(COMMAND "POINT" "9.926004,16.019672,0.487694")
(COMMAND "POINT" "10.074148,15.993420,0.432802")
(COMMAND "POINT" "10.220582,15.969179,0.380367")
(COMMAND "POINT" "10.365308,15.946950,0.330390")
(COMMAND "POINT" "10.508325,15.926732,0.282870")
(COMMAND "POINT" "10.649634,15.908525,0.237807")
(COMMAND "POINT" "10.789233,15.892330,0.195203")
(COMMAND "POINT" "10.927124,15.878146,0.155055")
(COMMAND "POINT" "11.063306,15.865973,0.117365")
(COMMAND "POINT" "11.197780,15.855811,0.082133")
(COMMAND "POINT" "11.330544,15.847660,0.049358")
(COMMAND "POINT" "11.461600,15.841521,0.019040")
(COMMAND "POINT" "11.590947,15.837392,-0.008820")
(COMMAND "POINT" "11.718586,15.835275,-0.034223")
(COMMAND "POINT" "11.844515,15.835170,-0.057168")
(COMMAND "POINT" "11.968736,15.837075,-0.077655")
(COMMAND "POINT" "12.091248,15.840992,-0.095685")
(COMMAND "POINT" "12.212051,15.846920,-0.111258")
(COMMAND "POINT" "12.331146,15.854859,-0.124373")
(COMMAND "POINT" "12.448532,15.864809,-0.135031")
(COMMAND "POINT" "12.564209,15.876771,-0.143231")
(COMMAND "POINT" "12.678177,15.890744,-0.148974")
(COMMAND "POINT" "12.790436,15.906728,-0.152259")
(COMMAND "POINT" "12.900987,15.924723,-0.153087")
(COMMAND "POINT" "13.009829,15.944730,-0.151458")
(COMMAND "POINT" "13.116962,15.966748,-0.147370")
(COMMAND "POINT" "13.222387,15.990777,-0.140826")
(COMMAND "POINT" "13.326102,16.016817,-0.131824")
(COMMAND "POINT" "13.428109,16.044868,-0.120364")
(COMMAND "POINT" "13.528407,16.074931,-0.106447")
(COMMAND "POINT" "13.626997,16.107005,-0.090073")
(COMMAND "POINT" "13.723878,16.141090,-0.071241")
(COMMAND "POINT" "13.819049,16.177186,-0.049951")
(COMMAND "POINT" "13.912513,16.215294,-0.026204")
(COMMAND "POINT" "14.004267,16.255412,0.000000")
(COMMAND "POINT" "2.757326,15.640894,2.068981")
(COMMAND "POINT" "2.764415,15.750105,2.149714")
(COMMAND "POINT" "2.774984,15.855808,2.226814")
(COMMAND "POINT" "2.789033,15.958003,2.300283")
(COMMAND "POINT" "2.806564,16.056690,2.370120")
(COMMAND "POINT" "2.827574,16.151870,2.436325")
(COMMAND "POINT" "2.852065,16.243541,2.498898")
(COMMAND "POINT" "2.880037,16.331705,2.557840")
(COMMAND "POINT" "2.911489,16.416361,2.613149")
(COMMAND "POINT" "2.946422,16.497509,2.664827")
(COMMAND "POINT" "2.984835,16.575149,2.712873")
(COMMAND "POINT" "3.026728,16.649281,2.757287")
(COMMAND "POINT" "3.072103,16.719906,2.798069")
(COMMAND "POINT" "3.120957,16.787023,2.835220")
(COMMAND "POINT" "3.173293,16.850631,2.868738")
(COMMAND "POINT" "3.229108,16.910732,2.898625")
(COMMAND "POINT" "3.288405,16.967326,2.924880")
(COMMAND "POINT" "3.351181,17.020411,2.947503")
(COMMAND "POINT" "3.417439,17.069989,2.966494")
(COMMAND "POINT" "3.487176,17.116058,2.981854")
(COMMAND "POINT" "3.560395,17.158620,2.993581")
(COMMAND "POINT" "3.637094,17.197674,3.001677")
(COMMAND "POINT" "3.717273,17.233220,3.006141")
(COMMAND "POINT" "3.800933,17.265259,3.006973")
(COMMAND "POINT" "3.888073,17.293789,3.004173")
(COMMAND "POINT" "3.978694,17.318812,2.997742")
(COMMAND "POINT" "4.072796,17.340327,2.987678")
(COMMAND "POINT" "4.170378,17.358334,2.973983")
(COMMAND "POINT" "4.271440,17.372833,2.956656")
(COMMAND "POINT" "4.375983,17.383824,2.935697")
(COMMAND "POINT" "4.484007,17.391308,2.911106")
(COMMAND "POINT" "4.595511,17.395283,2.882884")
(COMMAND "POINT" "4.710495,17.395751,2.851030")
(COMMAND "POINT" "4.828960,17.392711,2.815543")
(COMMAND "POINT" "4.950906,17.386163,2.776425")
(COMMAND "POINT" "5.076332,17.376108,2.733675")
(COMMAND "POINT" "5.205238,17.362544,2.687294")
(COMMAND "POINT" "5.337626,17.345473,2.637280")
(COMMAND "POINT" "5.473493,17.324894,2.583635")
(COMMAND "POINT" "5.612841,17.300807,2.526358")
(COMMAND "POINT" "5.755670,17.273212,2.465449")
(COMMAND "POINT" "5.901979,17.242109,2.400908")
(COMMAND "POINT" "6.051769,17.207498,2.332735")
(COMMAND "POINT" "6.205039,17.169380,2.260930")
(COMMAND "POINT" "6.361790,17.127754,2.185494")
(COMMAND "POINT" "6.522021,17.082620,2.106426")
(COMMAND "POINT" "6.685733,17.033978,2.023726")
(COMMAND "POINT" "6.852925,16.981828,1.937394")
(COMMAND "POINT" "7.023598,16.926171,1.847430")
(COMMAND "POINT" "7.197751,16.867005,1.753835")
(COMMAND "POINT" "7.374728,16.805024,1.657378")
(COMMAND "POINT" "7.550590,16.744378,1.562687")
(COMMAND "POINT" "7.724679,16.685760,1.470532")
(COMMAND "POINT" "7.896996,16.629169,1.380913")
(COMMAND "POINT" "8.067540,16.574605,1.293830")
(COMMAND "POINT" "8.236312,16.522068,1.209284")
(COMMAND "POINT" "8.403312,16.471559,1.127273")
(COMMAND "POINT" "8.568539,16.423078,1.047799")
(COMMAND "POINT" "8.731994,16.376623,0.970860")
(COMMAND "POINT" "8.893677,16.332196,0.896458")
(COMMAND "POINT" "9.053587,16.289797,0.824592")
(COMMAND "POINT" "9.211725,16.249424,0.755262")
(COMMAND "POINT" "9.368090,16.211079,0.688468")
(COMMAND "POINT" "9.522683,16.174762,0.624211")
(COMMAND "POINT" "9.675504,16.140472,0.562489")
(COMMAND "POINT" "9.826553,16.108209,0.503304")
(COMMAND "POINT" "9.975829,16.077973,0.446655")
(COMMAND "POINT" "10.123332,16.049765,0.392542")
(COMMAND "POINT" "10.269064,16.023585,0.340965")
(COMMAND "POINT" "10.413023,15.999431,0.291924")
(COMMAND "POINT" "10.555209,15.977305,0.245419")
(COMMAND "POINT" "10.695623,15.957206,0.201450")
(COMMAND "POINT" "10.834265,15.939135,0.160018")
(COMMAND "POINT" "10.971135,15.923091,0.121122")
(COMMAND "POINT" "11.106232,15.909074,0.084761")
(COMMAND "POINT" "11.239557,15.897085,0.050937")
(COMMAND "POINT" "11.371109,15.887123,0.019650")
(COMMAND "POINT" "11.500889,15.879189,-0.009102")
(COMMAND "POINT" "11.628897,15.873282,-0.035318")
(COMMAND "POINT" "11.755132,15.869402,-0.058997")
(COMMAND "POINT" "11.879595,15.867549,-0.080141")
(COMMAND "POINT" "12.002286,15.867724,-0.098748")
(COMMAND "POINT" "12.123204,15.869926,-0.114819")
(COMMAND "POINT" "12.242350,15.874156,-0.128354")
(COMMAND "POINT" "12.359724,15.880413,-0.139353")
(COMMAND "POINT" "12.475325,15.888697,-0.147816")
(COMMAND "POINT" "12.589154,15.899009,-0.153742")
(COMMAND "POINT" "12.701210,15.911348,-0.157133")
(COMMAND "POINT" "12.811494,15.925714,-0.157987")
(COMMAND "POINT" "12.920006,15.942108,-0.156305")
(COMMAND "POINT" "13.026745,15.960529,-0.152087")
(COMMAND "POINT" "13.131712,15.980978,-0.145333")
(COMMAND "POINT" "13.234907,16.003454,-0.136043")
(COMMAND "POINT" "13.336329,16.027957,-0.124217")
(COMMAND "POINT" "13.435979,16.054487,-0.109854")
(COMMAND "POINT" "13.533857,16.083045,-0.092956")
(COMMAND "POINT" "13.629962,16.113631,-0.073521")
(COMMAND "POINT" "13.724295,16.146243,-0.051550")
(COMMAND "POINT" "13.816855,16.180883,-0.027043")
(COMMAND "POINT" "13.907643,16.217550,0.000000")
(COMMAND "POINT" "2.704452,15.709230,2.133904")
(COMMAND "POINT" "2.706422,15.825919,2.217170")
(COMMAND "POINT" "2.712021,15.938860,2.296689")
(COMMAND "POINT" "2.721247,16.048051,2.372464")
(COMMAND "POINT" "2.734102,16.153495,2.444492")
(COMMAND "POINT" "2.750584,16.255189,2.512774")
(COMMAND "POINT" "2.770695,16.353135,2.577311")
(COMMAND "POINT" "2.794433,16.447332,2.638102")
(COMMAND "POINT" "2.821800,16.537780,2.695147")
(COMMAND "POINT" "2.852795,16.624479,2.748447")
(COMMAND "POINT" "2.887418,16.707430,2.798000")
(COMMAND "POINT" "2.925669,16.786633,2.843808")
(COMMAND "POINT" "2.967548,16.862086,2.885870")
(COMMAND "POINT" "3.013055,16.933791,2.924186")
(COMMAND "POINT" "3.062191,17.001747,2.958756")
(COMMAND "POINT" "3.114954,17.065955,2.989581")
(COMMAND "POINT" "3.171345,17.126414,3.016660")
(COMMAND "POINT" "3.231365,17.183124,3.039993")
(COMMAND "POINT" "3.295012,17.236086,3.059580")
(COMMAND "POINT" "3.362288,17.285298,3.075421")
(COMMAND "POINT" "3.433192,17.330763,3.087517")
(COMMAND "POINT" "3.507723,17.372478,3.095867")
(COMMAND "POINT" "3.585883,17.410445,3.100471")
(COMMAND "POINT" "3.667671,17.444663,3.101329")
(COMMAND "POINT" "3.753087,17.475132,3.098441")
(COMMAND "POINT" "3.842131,17.501853,3.091808")
(COMMAND "POINT" "3.934803,17.524825,3.081429")
(COMMAND "POINT" "4.031104,17.544049,3.067304")
(COMMAND "POINT" "4.131032,17.559523,3.049433")
(COMMAND "POINT" "4.234588,17.571249,3.027816")
(COMMAND "POINT" "4.341773,17.579227,3.002454")
(COMMAND "POINT" "4.452585,17.583455,2.973346")
(COMMAND "POINT" "4.567026,17.583935,2.940492")
(COMMAND "POINT" "4.685095,17.580667,2.903892")
(COMMAND "POINT" "4.806791,17.573649,2.863547")
(COMMAND "POINT" "4.932116,17.562883,2.819455")
(COMMAND "POINT" "5.061069,17.548369,2.771618")
(COMMAND "POINT" "5.193650,17.530105,2.720035")
(COMMAND "POINT" "5.329859,17.508093,2.664707")
(COMMAND "POINT" "5.469696,17.482332,2.605632")
(COMMAND "POINT" "5.613162,17.452823,2.542812")
(COMMAND "POINT" "5.760255,17.419565,2.476246")
(COMMAND "POINT" "5.910976,17.382558,2.405934")
(COMMAND "POINT" "6.065326,17.341803,2.331876")
(COMMAND "POINT" "6.223303,17.297298,2.254073")
(COMMAND "POINT" "6.384909,17.249046,2.172523")
(COMMAND "POINT" "6.550143,17.197044,2.087228")
(COMMAND "POINT" "6.719004,17.141294,1.998187")
(COMMAND "POINT" "6.891494,17.081795,1.905401")
(COMMAND "POINT" "7.067612,17.018547,1.808868")
(COMMAND "POINT" "7.246675,16.952275,1.709385")
(COMMAND "POINT" "7.424582,16.887322,1.611723")
(COMMAND "POINT" "7.600650,16.824412,1.516676")
(COMMAND "POINT" "7.774880,16.763544,1.424245")
(COMMAND "POINT" "7.947270,16.704720,1.334429")
(COMMAND "POINT" "8.117822,16.647938,1.247230")
(COMMAND "POINT" "8.286535,16.593200,1.162646")
(COMMAND "POINT" "8.453409,16.540504,1.080677")
(COMMAND "POINT" "8.618444,16.489851,1.001325")
(COMMAND "POINT" "8.781640,16.441241,0.924588")
(COMMAND "POINT" "8.942998,16.394675,0.850467")
(COMMAND "POINT" "9.102517,16.350151,0.778962")
(COMMAND "POINT" "9.260196,16.307670,0.710072")
(COMMAND "POINT" "9.416037,16.267232,0.643798")
(COMMAND "POINT" "9.570039,16.228837,0.580140")
(COMMAND "POINT" "9.722203,16.192485,0.519097")
(COMMAND "POINT" "9.872527,16.158176,0.460670")
(COMMAND "POINT" "10.021012,16.125909,0.404859")
(COMMAND "POINT" "10.167659,16.095686,0.351664")
(COMMAND "POINT" "10.312467,16.067506,0.301084")
(COMMAND "POINT" "10.455436,16.041369,0.253120")
(COMMAND "POINT" "10.596566,16.017274,0.207772")
(COMMAND "POINT" "10.735857,15.995223,0.165039")
(COMMAND "POINT" "10.873310,15.975214,0.124922")
(COMMAND "POINT" "11.008923,15.957249,0.087421")
(COMMAND "POINT" "11.142698,15.941326,0.052536")
(COMMAND "POINT" "11.274634,15.927446,0.020266")
(COMMAND "POINT" "11.404731,15.915609,-0.009388")
(COMMAND "POINT" "11.532989,15.905816,-0.036426")
(COMMAND "POINT" "11.659408,15.898065,-0.060849")
(COMMAND "POINT" "11.783989,15.892357,-0.082656")
(COMMAND "POINT" "11.906730,15.888692,-0.101847")
(COMMAND "POINT" "12.027633,15.887070,-0.118422")
(COMMAND "POINT" "12.146697,15.887491,-0.132382")
(COMMAND "POINT" "12.263922,15.889954,-0.143726")
(COMMAND "POINT" "12.379308,15.894461,-0.152454")
(COMMAND "POINT" "12.492856,15.901011,-0.158567")
(COMMAND "POINT" "12.604564,15.909604,-0.162063")
(COMMAND "POINT" "12.714434,15.920239,-0.162945")
(COMMAND "POINT" "12.822465,15.932918,-0.161210")
(COMMAND "POINT" "12.928657,15.947639,-0.156860")
(COMMAND "POINT" "13.033010,15.964404,-0.149894")
(COMMAND "POINT" "13.135524,15.983211,-0.140312")
(COMMAND "POINT" "13.236199,16.004061,-0.128115")
(COMMAND "POINT" "13.335036,16.026955,-0.113301")
(COMMAND "POINT" "13.432034,16.051891,-0.095873")
(COMMAND "POINT" "13.527192,16.078870,-0.075828")
(COMMAND "POINT" "13.620512,16.107892,-0.053168")
(COMMAND "POINT" "13.711994,16.138957,-0.027892")
(COMMAND "POINT" "13.801636,16.172065,0.000000")
(COMMAND "POINT" "2.652980,15.776867,2.199580")
(COMMAND "POINT" "2.649655,15.901024,2.285409")
(COMMAND "POINT" "2.650108,16.021190,2.367376")
(COMMAND "POINT" "2.654340,16.137366,2.445482")
(COMMAND "POINT" "2.662350,16.249550,2.519728")
(COMMAND "POINT" "2.674139,16.357744,2.590112")
(COMMAND "POINT" "2.689706,16.461946,2.656635")
(COMMAND "POINT" "2.709052,16.562158,2.719297")
(COMMAND "POINT" "2.732176,16.658378,2.778097")
(COMMAND "POINT" "2.759079,16.750608,2.833037")
(COMMAND "POINT" "2.789760,16.838846,2.884116")
(COMMAND "POINT" "2.824219,16.923094,2.931333")
(COMMAND "POINT" "2.862457,17.003351,2.974690")
(COMMAND "POINT" "2.904474,17.079616,3.014185")
(COMMAND "POINT" "2.950269,17.151891,3.049820")
(COMMAND "POINT" "2.999843,17.220175,3.081593")
(COMMAND "POINT" "3.053194,17.284467,3.109505")
(COMMAND "POINT" "3.110325,17.344769,3.133556")
(COMMAND "POINT" "3.171234,17.401080,3.153746")
(COMMAND "POINT" "3.235921,17.453400,3.170075")
(COMMAND "POINT" "3.304387,17.501729,3.182543")
(COMMAND "POINT" "3.376631,17.546066,3.191150")
(COMMAND "POINT" "3.452654,17.586413,3.195896")
(COMMAND "POINT" "3.532455,17.622769,3.196780")
(COMMAND "POINT" "3.616035,17.655134,3.193804")
(COMMAND "POINT" "3.703393,17.683508,3.186966")
(COMMAND "POINT" "3.794530,17.707891,3.176268")
(COMMAND "POINT" "3.889445,17.728283,3.161708")
(COMMAND "POINT" "3.988139,17.744684,3.143287")
(COMMAND "POINT" "4.090611,17.757094,3.121005")
(COMMAND "POINT" "4.196862,17.765513,3.094862")
(COMMAND "POINT" "4.306891,17.769942,3.064858")
(COMMAND "POINT" "4.420698,17.770379,3.030993")
(COMMAND "POINT" "4.538284,17.766825,2.993267")
(COMMAND "POINT" "4.659649,17.759280,2.951680")
(COMMAND "POINT" "4.784791,17.747744,2.906232")
(COMMAND "POINT" "4.913713,17.732218,2.856922")
(COMMAND "POINT" "5.046413,17.712700,2.803752")
(COMMAND "POINT" "5.182891,17.689191,2.746720")
(COMMAND "POINT" "5.323148,17.661692,2.685827")
(COMMAND "POINT" "5.467183,17.630201,2.621074")
(COMMAND "POINT" "5.614997,17.594719,2.552459")
(COMMAND "POINT" "5.766589,17.555247,2.479983")
(COMMAND "POINT" "5.921960,17.511783,2.403646")
(COMMAND "POINT" "6.081109,17.464329,2.323448")
(COMMAND "POINT" "6.244037,17.412883,2.239388")
(COMMAND "POINT" "6.410743,17.357447,2.151468")
(COMMAND "POINT" "6.581228,17.298019,2.059687")
(COMMAND "POINT" "6.755491,17.234601,1.964044")
(COMMAND "POINT" "6.933532,17.167191,1.864541")
(COMMAND "POINT" "7.114641,17.096547,1.761996")
(COMMAND "POINT" "7.294553,17.027205,1.661328")
(COMMAND "POINT" "7.472557,16.959920,1.563356")
(COMMAND "POINT" "7.648652,16.894694,1.468080")
(COMMAND "POINT" "7.822839,16.831526,1.375500")
(COMMAND "POINT" "7.995118,16.770415,1.285616")
(COMMAND "POINT" "8.165489,16.711363,1.198429")
(COMMAND "POINT" "8.333951,16.654368,1.113938")
(COMMAND "POINT" "8.500505,16.599432,1.032143")
(COMMAND "POINT" "8.665151,16.546553,0.953045")
(COMMAND "POINT" "8.827889,16.495733,0.876642")
(COMMAND "POINT" "8.988719,16.446970,0.802936")
(COMMAND "POINT" "9.147640,16.400265,0.731926")
(COMMAND "POINT" "9.304653,16.355619,0.663612")
(COMMAND "POINT" "9.459758,16.313030,0.597995")
(COMMAND "POINT" "9.612955,16.272499,0.535074")
(COMMAND "POINT" "9.764243,16.234027,0.474849")
(COMMAND "POINT" "9.913623,16.197612,0.417320")
(COMMAND "POINT" "10.061095,16.163255,0.362487")
(COMMAND "POINT" "10.206659,16.130957,0.310351")
(COMMAND "POINT" "10.350314,16.100716,0.260910")
(COMMAND "POINT" "10.492062,16.072533,0.214166")
(COMMAND "POINT" "10.631901,16.046408,0.170119")
(COMMAND "POINT" "10.769831,16.022342,0.128767")
(COMMAND "POINT" "10.905854,16.000333,0.090112")
(COMMAND "POINT" "11.039968,15.980382,0.054153")
(COMMAND "POINT" "11.172175,15.962489,0.020890")
(COMMAND "POINT" "11.302472,15.946654,-0.009677")
(COMMAND "POINT" "11.430862,15.932877,-0.037547")
(COMMAND "POINT" "11.557344,15.921159,-0.062721")
(COMMAND "POINT" "11.681917,15.911498,-0.085199")
(COMMAND "POINT" "11.804582,15.903895,-0.104981")
(COMMAND "POINT" "11.925339,15.898350,-0.122067")
(COMMAND "POINT" "12.044187,15.894863,-0.136456")
(COMMAND "POINT" "12.161127,15.893434,-0.148149")
(COMMAND "POINT" "12.276159,15.894063,-0.157146")
(COMMAND "POINT" "12.389283,15.896750,-0.163447")
(COMMAND "POINT" "12.500499,15.901495,-0.167051")
(COMMAND "POINT" "12.609806,15.908298,-0.167960")
(COMMAND "POINT" "12.717206,15.917158,-0.166172")
(COMMAND "POINT" "12.822697,15.928077,-0.161688")
(COMMAND "POINT" "12.926279,15.941054,-0.154507")
(COMMAND "POINT" "13.027954,15.956089,-0.144630")
(COMMAND "POINT" "13.127720,15.973182,-0.132058")
(COMMAND "POINT" "13.225578,15.992333,-0.116789")
(COMMAND "POINT" "13.321528,16.013542,-0.098823")
(COMMAND "POINT" "13.415569,16.036808,-0.078162")
(COMMAND "POINT" "13.507703,16.062133,-0.054804")
(COMMAND "POINT" "13.597928,16.089516,-0.028750")
(COMMAND "POINT" "13.686245,16.118957,0.000000")
(COMMAND "POINT" "2.602910,15.843803,2.266011")
(COMMAND "POINT" "2.594112,15.975419,2.354431")
(COMMAND "POINT" "2.589246,16.102800,2.438874")
(COMMAND "POINT" "2.588312,16.225946,2.519339")
(COMMAND "POINT" "2.591309,16.344857,2.595827")
(COMMAND "POINT" "2.598239,16.459534,2.668336")
(COMMAND "POINT" "2.609100,16.569976,2.736869")
(COMMAND "POINT" "2.623892,16.676183,2.801423")
(COMMAND "POINT" "2.642616,16.778156,2.862000")
(COMMAND "POINT" "2.665272,16.875893,2.918599")
(COMMAND "POINT" "2.691860,16.969397,2.971220")
(COMMAND "POINT" "2.722380,17.058665,3.019864")
(COMMAND "POINT" "2.756831,17.143699,3.064530")
(COMMAND "POINT" "2.795214,17.224497,3.105218")
(COMMAND "POINT" "2.837528,17.301062,3.141928")
(COMMAND "POINT" "2.883774,17.373391,3.174661")
(COMMAND "POINT" "2.933952,17.441486,3.203417")
(COMMAND "POINT" "2.988062,17.505346,3.228194")
(COMMAND "POINT" "3.046103,17.564971,3.248994")
(COMMAND "POINT" "3.108076,17.620362,3.265816")
(COMMAND "POINT" "3.173981,17.671518,3.278660")
(COMMAND "POINT" "3.243818,17.718439,3.287527")
(COMMAND "POINT" "3.317586,17.761126,3.292416")
(COMMAND "POINT" "3.395286,17.799577,3.293327")
(COMMAND "POINT" "3.476917,17.833794,3.290261")
(COMMAND "POINT" "3.562481,17.863777,3.283217")
(COMMAND "POINT" "3.651976,17.889524,3.272195")
(COMMAND "POINT" "3.745402,17.911037,3.257196")
(COMMAND "POINT" "3.842761,17.928315,3.238219")
(COMMAND "POINT" "3.944051,17.941359,3.215264")
(COMMAND "POINT" "4.049273,17.950167,3.188331")
(COMMAND "POINT" "4.158426,17.954742,3.157421")
(COMMAND "POINT" "4.271511,17.955081,3.122533")
(COMMAND "POINT" "4.388528,17.951185,3.083668")
(COMMAND "POINT" "4.509477,17.943055,3.040825")
(COMMAND "POINT" "4.634357,17.930690,2.994004")
(COMMAND "POINT" "4.763169,17.914091,2.943205")
(COMMAND "POINT" "4.895913,17.893257,2.888429")
(COMMAND "POINT" "5.032589,17.868188,2.829675")
(COMMAND "POINT" "5.173196,17.838884,2.766943")
(COMMAND "POINT" "5.317735,17.805345,2.700233")
(COMMAND "POINT" "5.466205,17.767572,2.629546")
(COMMAND "POINT" "5.618608,17.725564,2.554882")
(COMMAND "POINT" "5.774942,17.679322,2.476239")
(COMMAND "POINT" "5.935207,17.628845,2.393619")
(COMMAND "POINT" "6.099405,17.574133,2.307021")
(COMMAND "POINT" "6.267534,17.515186,2.216445")
(COMMAND "POINT" "6.439595,17.452004,2.121892")
(COMMAND "POINT" "6.615587,17.384588,2.023361")
(COMMAND "POINT" "6.795511,17.312937,1.920853")
(COMMAND "POINT" "6.978628,17.237840,1.815211")
(COMMAND "POINT" "7.160504,17.164027,1.711502")
(COMMAND "POINT" "7.340399,17.092286,1.610571")
(COMMAND "POINT" "7.518313,17.022618,1.512418")
(COMMAND "POINT" "7.694247,16.955022,1.417042")
(COMMAND "POINT" "7.868201,16.889499,1.324444")
(COMMAND "POINT" "8.040174,16.826048,1.234623")
(COMMAND "POINT" "8.210166,16.764670,1.147581")
(COMMAND "POINT" "8.378178,16.705364,1.063315")
(COMMAND "POINT" "8.544210,16.648131,0.981828")
(COMMAND "POINT" "8.708261,16.592970,0.903118")
(COMMAND "POINT" "8.870331,16.539882,0.827186")
(COMMAND "POINT" "9.030421,16.488866,0.754031")
(COMMAND "POINT" "9.188531,16.439922,0.683654")
(COMMAND "POINT" "9.344660,16.393051,0.616055")
(COMMAND "POINT" "9.498809,16.348253,0.551234")
(COMMAND "POINT" "9.650977,16.305527,0.489190")
(COMMAND "POINT" "9.801164,16.264873,0.429923")
(COMMAND "POINT" "9.949372,16.226292,0.373435")
(COMMAND "POINT" "10.095598,16.189783,0.319724")
(COMMAND "POINT" "10.239844,16.155347,0.268790")
(COMMAND "POINT" "10.382110,16.122984,0.220635")
(COMMAND "POINT" "10.522395,16.092692,0.175257")
(COMMAND "POINT" "10.660700,16.064474,0.132656")
(COMMAND "POINT" "10.797024,16.038327,0.092833")
(COMMAND "POINT" "10.931368,16.014254,0.055788")
(COMMAND "POINT" "11.063731,15.992252,0.021521")
(COMMAND "POINT" "11.194114,15.972324,-0.009969")
(COMMAND "POINT" "11.322516,15.954467,-0.038681")
(COMMAND "POINT" "11.448938,15.938683,-0.064616")
(COMMAND "POINT" "11.573379,15.924972,-0.087773")
(COMMAND "POINT" "11.695840,15.913333,-0.108152")
(COMMAND "POINT" "11.816320,15.903766,-0.125753")
(COMMAND "POINT" "11.934820,15.896272,-0.140577")
(COMMAND "POINT" "12.051339,15.890851,-0.152624")
(COMMAND "POINT" "12.165878,15.887502,-0.161892")
(COMMAND "POINT" "12.278436,15.886225,-0.168383")
(COMMAND "POINT" "12.389014,15.887021,-0.172097")
(COMMAND "POINT" "12.497612,15.889889,-0.173032")
(COMMAND "POINT" "12.604229,15.894830,-0.171190")
(COMMAND "POINT" "12.708865,15.901844,-0.166571")
(COMMAND "POINT" "12.811521,15.910929,-0.159173")
(COMMAND "POINT" "12.912196,15.922088,-0.148999")
(COMMAND "POINT" "13.010891,15.935318,-0.136046")
(COMMAND "POINT" "13.107606,15.950622,-0.120316")
(COMMAND "POINT" "13.202340,15.967997,-0.101808")
(COMMAND "POINT" "13.295093,15.987445,-0.080522")
(COMMAND "POINT" "13.385866,16.008966,-0.056459")
(COMMAND "POINT" "13.474659,16.032559,-0.029618")
(COMMAND "POINT" "13.561471,16.058225,0.000000")
(COMMAND "POINT" "2.554242,15.910041,2.333195")
(COMMAND "POINT" "2.539794,16.049104,2.424237")
(COMMAND "POINT" "2.529435,16.183688,2.511183")
(COMMAND "POINT" "2.523163,16.313792,2.594034")
(COMMAND "POINT" "2.520979,16.439416,2.672789")
(COMMAND "POINT" "2.522883,16.560560,2.747449")
(COMMAND "POINT" "2.528875,16.677224,2.818013")
(COMMAND "POINT" "2.538954,16.789408,2.884481")
(COMMAND "POINT" "2.553121,16.897112,2.946854")
(COMMAND "POINT" "2.571376,17.000337,3.005131")
(COMMAND "POINT" "2.593719,17.099081,3.059313")
(COMMAND "POINT" "2.620150,17.193346,3.109398")
(COMMAND "POINT" "2.650668,17.283130,3.155389")
(COMMAND "POINT" "2.685274,17.368435,3.197283")
(COMMAND "POINT" "2.723968,17.449260,3.235082")
(COMMAND "POINT" "2.766749,17.525605,3.268786")
(COMMAND "POINT" "2.813619,17.597470,3.298393")
(COMMAND "POINT" "2.864576,17.664855,3.323906")
(COMMAND "POINT" "2.919621,17.727760,3.345322")
(COMMAND "POINT" "2.978753,17.786185,3.362643")
(COMMAND "POINT" "3.041974,17.840131,3.375868")
(COMMAND "POINT" "3.109282,17.889596,3.384998")
(COMMAND "POINT" "3.180678,17.934582,3.390032")
(COMMAND "POINT" "3.256162,17.975087,3.390970")
(COMMAND "POINT" "3.335733,18.011113,3.387813")
(COMMAND "POINT" "3.419393,18.042659,3.380560")
(COMMAND "POINT" "3.507140,18.069725,3.369211")
(COMMAND "POINT" "3.598975,18.092311,3.353767")
(COMMAND "POINT" "3.694897,18.110417,3.334227")
(COMMAND "POINT" "3.794908,18.124043,3.310592")
(COMMAND "POINT" "3.899006,18.133189,3.282861")
(COMMAND "POINT" "4.007192,18.137855,3.251034")
(COMMAND "POINT" "4.119466,18.138042,3.215112")
(COMMAND "POINT" "4.235827,18.133748,3.175094")
(COMMAND "POINT" "4.356277,18.124975,3.130981")
(COMMAND "POINT" "4.480814,18.111722,3.082772")
(COMMAND "POINT" "4.609439,18.093988,3.030467")
(COMMAND "POINT" "4.742151,18.071775,2.974067")
(COMMAND "POINT" "4.878952,18.045082,2.913571")
(COMMAND "POINT" "5.019840,18.013909,2.848979")
(COMMAND "POINT" "5.164816,17.978257,2.780292")
(COMMAND "POINT" "5.313880,17.938124,2.707509")
(COMMAND "POINT" "5.467031,17.893511,2.630630")
(COMMAND "POINT" "5.624270,17.844419,2.549656")
(COMMAND "POINT" "5.785598,17.790846,2.464586")
(COMMAND "POINT" "5.951012,17.732794,2.375421")
(COMMAND "POINT" "6.120515,17.670261,2.282160")
(COMMAND "POINT" "6.294105,17.603249,2.184803")
(COMMAND "POINT" "6.471784,17.531757,2.083351")
(COMMAND "POINT" "6.653549,17.455785,1.977803")
(COMMAND "POINT" "6.838635,17.376154,1.869029")
(COMMAND "POINT" "7.022433,17.297788,1.762246")
(COMMAND "POINT" "7.204176,17.221509,1.658322")
(COMMAND "POINT" "7.383863,17.147317,1.557259")
(COMMAND "POINT" "7.561494,17.075210,1.459055")
(COMMAND "POINT" "7.737069,17.005190,1.363712")
(COMMAND "POINT" "7.910589,16.937257,1.271228")
(COMMAND "POINT" "8.082053,16.871410,1.181605")
(COMMAND "POINT" "8.251462,16.807649,1.094841")
(COMMAND "POINT" "8.418815,16.745975,1.010938")
(COMMAND "POINT" "8.584112,16.686387,0.929894")
(COMMAND "POINT" "8.747354,16.628886,0.851711")
(COMMAND "POINT" "8.908540,16.573471,0.776387")
(COMMAND "POINT" "9.067671,16.520143,0.703924")
(COMMAND "POINT" "9.224745,16.468901,0.634320")
(COMMAND "POINT" "9.379765,16.419745,0.567577")
(COMMAND "POINT" "9.532728,16.372676,0.503693")
(COMMAND "POINT" "9.683636,16.327693,0.442670")
(COMMAND "POINT" "9.832488,16.284796,0.384506")
(COMMAND "POINT" "9.979285,16.243986,0.329203")
(COMMAND "POINT" "10.124026,16.205263,0.276760")
(COMMAND "POINT" "10.266711,16.168625,0.227176")
(COMMAND "POINT" "10.407341,16.134075,0.180453")
(COMMAND "POINT" "10.545915,16.101610,0.136589")
(COMMAND "POINT" "10.682433,16.071232,0.095586")
(COMMAND "POINT" "10.816896,16.042941,0.057442")
(COMMAND "POINT" "10.949303,16.016736,0.022159")
(COMMAND "POINT" "11.079655,15.992617,-0.010265")
(COMMAND "POINT" "11.207951,15.970585,-0.039828")
(COMMAND "POINT" "11.334191,15.950639,-0.066532")
(COMMAND "POINT" "11.458376,15.932779,-0.090375")
(COMMAND "POINT" "11.580505,15.917006,-0.111358")
(COMMAND "POINT" "11.700578,15.903320,-0.129482")
(COMMAND "POINT" "11.818596,15.891720,-0.144745")
(COMMAND "POINT" "11.934558,15.882206,-0.157149")
(COMMAND "POINT" "12.048464,15.874779,-0.166692")
(COMMAND "POINT" "12.160315,15.869438,-0.173376")
(COMMAND "POINT" "12.270110,15.866183,-0.177199")
(COMMAND "POINT" "12.377850,15.865015,-0.178162")
(COMMAND "POINT" "12.483534,15.865933,-0.176266")
(COMMAND "POINT" "12.587162,15.868938,-0.171509")
(COMMAND "POINT" "12.688735,15.874029,-0.163893")
(COMMAND "POINT" "12.788252,15.881207,-0.153416")
(COMMAND "POINT" "12.885713,15.890471,-0.140080")
(COMMAND "POINT" "12.981119,15.901821,-0.123883")
(COMMAND "POINT" "13.074469,15.915258,-0.104826")
(COMMAND "POINT" "13.165763,15.930781,-0.082910")
(COMMAND "POINT" "13.255002,15.948391,-0.058133")
(COMMAND "POINT" "13.342185,15.968087,-0.030497")
(COMMAND "POINT" "13.427313,15.989869,0.000000")
(COMMAND "POINT" "2.506976,15.975578,2.401133")
(COMMAND "POINT" "2.486702,16.122080,2.494826")
(COMMAND "POINT" "2.470674,16.263855,2.584304")
(COMMAND "POINT" "2.458894,16.400904,2.669567")
(COMMAND "POINT" "2.451360,16.533226,2.750616")
(COMMAND "POINT" "2.448073,16.660821,2.827449")
(COMMAND "POINT" "2.449032,16.783690,2.900068")
(COMMAND "POINT" "2.454238,16.901832,2.968472")
(COMMAND "POINT" "2.463691,17.015248,3.032660")
(COMMAND "POINT" "2.477390,17.123937,3.092635")
(COMMAND "POINT" "2.495336,17.227900,3.148394")
(COMMAND "POINT" "2.517529,17.327136,3.199938")
(COMMAND "POINT" "2.543969,17.421646,3.247267")
(COMMAND "POINT" "2.574655,17.511429,3.290382")
(COMMAND "POINT" "2.609588,17.596485,3.329281")
(COMMAND "POINT" "2.648767,17.676815,3.363966")
(COMMAND "POINT" "2.692194,17.752419,3.394436")
(COMMAND "POINT" "2.739866,17.823295,3.420691")
(COMMAND "POINT" "2.791786,17.889446,3.442731")
(COMMAND "POINT" "2.847952,17.950869,3.460556")
(COMMAND "POINT" "2.908365,18.007567,3.474167")
(COMMAND "POINT" "2.973025,18.059537,3.483562")
(COMMAND "POINT" "3.041931,18.106781,3.488743")
(COMMAND "POINT" "3.115084,18.149299,3.489708")
(COMMAND "POINT" "3.192484,18.187090,3.486459")
(COMMAND "POINT" "3.274130,18.220154,3.478995")
(COMMAND "POINT" "3.360023,18.248492,3.467316")
(COMMAND "POINT" "3.450163,18.272103,3.451422")
(COMMAND "POINT" "3.544549,18.290988,3.431313")
(COMMAND "POINT" "3.643182,18.305146,3.406990")
(COMMAND "POINT" "3.746062,18.314578,3.378451")
(COMMAND "POINT" "3.853188,18.319283,3.345698")
(COMMAND "POINT" "3.964562,18.319262,3.308730")
(COMMAND "POINT" "4.080181,18.314514,3.267547")
(COMMAND "POINT" "4.200048,18.305039,3.222149")
(COMMAND "POINT" "4.324161,18.290838,3.172536")
(COMMAND "POINT" "4.452521,18.271910,3.118708")
(COMMAND "POINT" "4.585127,18.248256,3.060665")
(COMMAND "POINT" "4.721981,18.219875,2.998408")
(COMMAND "POINT" "4.863080,18.186768,2.931935")
(COMMAND "POINT" "5.008427,18.148934,2.861248")
(COMMAND "POINT" "5.158020,18.106374,2.786346")
(COMMAND "POINT" "5.311860,18.059087,2.707229")
(COMMAND "POINT" "5.469947,18.007073,2.623897")
(COMMAND "POINT" "5.632280,17.950333,2.536350")
(COMMAND "POINT" "5.798860,17.888867,2.444588")
(COMMAND "POINT" "5.969687,17.822674,2.348612")
(COMMAND "POINT" "6.144760,17.751754,2.248420")
(COMMAND "POINT" "6.324080,17.676108,2.144014")
(COMMAND "POINT" "6.507647,17.595735,2.035393")
(COMMAND "POINT" "6.694662,17.511489,1.923452")
(COMMAND "POINT" "6.880342,17.428489,1.813559")
(COMMAND "POINT" "7.063888,17.347589,1.706609")
(COMMAND "POINT" "7.245301,17.268789,1.602603")
(COMMAND "POINT" "7.424579,17.192089,1.501540")
(COMMAND "POINT" "7.601724,17.117489,1.403420")
(COMMAND "POINT" "7.776736,17.044988,1.308244")
(COMMAND "POINT" "7.949613,16.974588,1.216011")
(COMMAND "POINT" "8.120357,16.906287,1.126721")
(COMMAND "POINT" "8.288968,16.840086,1.040374")
(COMMAND "POINT" "8.455444,16.775985,0.956971")
(COMMAND "POINT" "8.619787,16.713983,0.876511")
(COMMAND "POINT" "8.781997,16.654082,0.798994")
(COMMAND "POINT" "8.942072,16.596280,0.724421")
(COMMAND "POINT" "9.100014,16.540578,0.652790")
(COMMAND "POINT" "9.255822,16.486976,0.584104")
(COMMAND "POINT" "9.409497,16.435473,0.518360")
(COMMAND "POINT" "9.561038,16.386071,0.455560")
(COMMAND "POINT" "9.710445,16.338768,0.395703")
(COMMAND "POINT" "9.857719,16.293565,0.338789")
(COMMAND "POINT" "10.002859,16.250462,0.284818")
(COMMAND "POINT" "10.145865,16.209459,0.233791")
(COMMAND "POINT" "10.286738,16.170555,0.185707")
(COMMAND "POINT" "10.425477,16.133751,0.140566")
(COMMAND "POINT" "10.562082,16.099048,0.098369")
(COMMAND "POINT" "10.696554,16.066444,0.059115")
(COMMAND "POINT" "10.828892,16.035939,0.022804")
(COMMAND "POINT" "10.959096,16.007535,-0.010564")
(COMMAND "POINT" "11.087167,15.981230,-0.040988")
(COMMAND "POINT" "11.213103,15.957025,-0.068469")
(COMMAND "POINT" "11.336907,15.934920,-0.093007")
(COMMAND "POINT" "11.458576,15.914915,-0.114601")
(COMMAND "POINT" "11.578112,15.897010,-0.133252")
(COMMAND "POINT" "11.695514,15.881204,-0.148960")
(COMMAND "POINT" "11.810783,15.867499,-0.161725")
(COMMAND "POINT" "11.923918,15.855893,-0.171546")
(COMMAND "POINT" "12.034919,15.846387,-0.178424")
(COMMAND "POINT" "12.143787,15.838980,-0.182359")
(COMMAND "POINT" "12.250521,15.833674,-0.183350")
(COMMAND "POINT" "12.355121,15.830467,-0.181398")
(COMMAND "POINT" "12.457587,15.829360,-0.176503")
(COMMAND "POINT" "12.557920,15.830353,-0.168665")
(COMMAND "POINT" "12.656120,15.833446,-0.157883")
(COMMAND "POINT" "12.752185,15.838639,-0.144158")
(COMMAND "POINT" "12.846117,15.845931,-0.127490")
(COMMAND "POINT" "12.937915,15.855323,-0.107879")
(COMMAND "POINT" "13.027580,15.866816,-0.085324")
(COMMAND "POINT" "13.115111,15.880407,-0.059826")
(COMMAND "POINT" "13.200508,15.896099,-0.031385")
(COMMAND "POINT" "13.283771,15.913891,0.000000")
(COMMAND "POINT" "2.461112,16.040416,2.469824")
(COMMAND "POINT" "2.434834,16.194346,2.566198")
(COMMAND "POINT" "2.412965,16.343301,2.658236")
(COMMAND "POINT" "2.395504,16.487281,2.745938")
(COMMAND "POINT" "2.382451,16.626287,2.829305")
(COMMAND "POINT" "2.373807,16.760318,2.908337")
(COMMAND "POINT" "2.369571,16.889374,2.983033")
(COMMAND "POINT" "2.369744,17.013456,3.053394")
(COMMAND "POINT" "2.374325,17.132563,3.119419")
(COMMAND "POINT" "2.383314,17.246695,3.181109")
(COMMAND "POINT" "2.396712,17.355853,3.238463")
(COMMAND "POINT" "2.414519,17.460036,3.291482")
(COMMAND "POINT" "2.436734,17.559245,3.340165")
(COMMAND "POINT" "2.463357,17.653479,3.384513")
(COMMAND "POINT" "2.494388,17.742738,3.424526")
(COMMAND "POINT" "2.529829,17.827023,3.460203")
(COMMAND "POINT" "2.569677,17.906333,3.491544")
(COMMAND "POINT" "2.613934,17.980668,3.518550")
(COMMAND "POINT" "2.662599,18.050029,3.541221")
(COMMAND "POINT" "2.715673,18.114415,3.559556")
(COMMAND "POINT" "2.773155,18.173826,3.573556")
(COMMAND "POINT" "2.835046,18.228263,3.583220")
(COMMAND "POINT" "2.901345,18.277725,3.588549")
(COMMAND "POINT" "2.972052,18.322212,3.589542")
(COMMAND "POINT" "3.047168,18.361725,3.586200")
(COMMAND "POINT" "3.126693,18.396263,3.578522")
(COMMAND "POINT" "3.210625,18.425827,3.566509")
(COMMAND "POINT" "3.298966,18.450416,3.550161")
(COMMAND "POINT" "3.391716,18.470030,3.529477")
(COMMAND "POINT" "3.488874,18.484670,3.504457")
(COMMAND "POINT" "3.590440,18.494335,3.475102")
(COMMAND "POINT" "3.696415,18.499025,3.441412")
(COMMAND "POINT" "3.806799,18.498740,3.403386")
(COMMAND "POINT" "3.921590,18.493482,3.361025")
(COMMAND "POINT" "4.040790,18.483248,3.314328")
(COMMAND "POINT" "4.164399,18.468040,3.263296")
(COMMAND "POINT" "4.292416,18.447857,3.207928")
(COMMAND "POINT" "4.424841,18.422699,3.148225")
(COMMAND "POINT" "4.561675,18.392567,3.084186")
(COMMAND "POINT" "4.702917,18.357460,3.015812")
(COMMAND "POINT" "4.848568,18.317379,2.943103")
(COMMAND "POINT" "4.998627,18.272322,2.866058")
(COMMAND "POINT" "5.153094,18.222292,2.784678")
(COMMAND "POINT" "5.311970,18.167286,2.698962")
(COMMAND "POINT" "5.475255,18.107306,2.608910")
(COMMAND "POINT" "5.642948,18.042352,2.514523")
(COMMAND "POINT" "5.815049,17.972422,2.415801")
(COMMAND "POINT" "5.991558,17.897518,2.312743")
(COMMAND "POINT" "6.172476,17.817640,2.205350")
(COMMAND "POINT" "6.357803,17.732786,2.093622")
(COMMAND "POINT" "6.546710,17.643844,1.978478")
(COMMAND "POINT" "6.734230,17.556129,1.865441")
(COMMAND "POINT" "6.919536,17.470526,1.755432")
(COMMAND "POINT" "7.102627,17.387036,1.648450")
(COMMAND "POINT" "7.283504,17.305659,1.544496")
(COMMAND "POINT" "7.462165,17.226395,1.443569")
(COMMAND "POINT" "7.638613,17.149243,1.345670")
(COMMAND "POINT" "7.812846,17.074203,1.250798")
(COMMAND "POINT" "7.984864,17.001277,1.158954")
(COMMAND "POINT" "8.154667,16.930463,1.070137")
(COMMAND "POINT" "8.322256,16.861761,0.984348")
(COMMAND "POINT" "8.487631,16.795173,0.901586")
(COMMAND "POINT" "8.650790,16.730697,0.821852")
(COMMAND "POINT" "8.811736,16.668334,0.745145")
(COMMAND "POINT" "8.970466,16.608083,0.671466")
(COMMAND "POINT" "9.126982,16.549945,0.600814")
(COMMAND "POINT" "9.281284,16.493920,0.533189")
(COMMAND "POINT" "9.433371,16.440007,0.468592")
(COMMAND "POINT" "9.583243,16.388207,0.407023")
(COMMAND "POINT" "9.730901,16.338520,0.348481")
(COMMAND "POINT" "9.876344,16.290945,0.292966")
(COMMAND "POINT" "10.019572,16.245483,0.240479")
(COMMAND "POINT" "10.160586,16.202134,0.191020")
(COMMAND "POINT" "10.299385,16.160897,0.144588")
(COMMAND "POINT" "10.435970,16.121773,0.101183")
(COMMAND "POINT" "10.570340,16.084762,0.060806")
(COMMAND "POINT" "10.702496,16.049863,0.023456")
(COMMAND "POINT" "10.832437,16.017077,-0.010866")
(COMMAND "POINT" "10.960163,15.986404,-0.042160")
(COMMAND "POINT" "11.085675,15.957843,-0.070428")
(COMMAND "POINT" "11.208972,15.931395,-0.095667")
(COMMAND "POINT" "11.330055,15.907060,-0.117879")
(COMMAND "POINT" "11.448923,15.884837,-0.137064")
(COMMAND "POINT" "11.565576,15.864727,-0.153221")
(COMMAND "POINT" "11.680015,15.846729,-0.166351")
(COMMAND "POINT" "11.792239,15.830845,-0.176453")
(COMMAND "POINT" "11.902249,15.817073,-0.183528")
(COMMAND "POINT" "12.010044,15.805413,-0.187576")
(COMMAND "POINT" "12.115624,15.795867,-0.188595")
(COMMAND "POINT" "12.218990,15.788433,-0.186588")
(COMMAND "POINT" "12.320141,15.783111,-0.181553")
(COMMAND "POINT" "12.419078,15.779902,-0.173490")
(COMMAND "POINT" "12.515800,15.778806,-0.162400")
(COMMAND "POINT" "12.610308,15.779823,-0.148282")
(COMMAND "POINT" "12.702601,15.782952,-0.131137")
(COMMAND "POINT" "12.792679,15.788194,-0.110965")
(COMMAND "POINT" "12.880543,15.795549,-0.087765")
(COMMAND "POINT" "12.966192,15.805016,-0.061537")
(COMMAND "POINT" "13.049626,15.816596,-0.032282")
(COMMAND "POINT" "13.130846,15.830288,0.000000")
(COMMAND "POINT" "2.416650,16.104554,2.539270")
(COMMAND "POINT" "2.384191,16.265902,2.638353")
(COMMAND "POINT" "2.356305,16.422025,2.732979")
(COMMAND "POINT" "2.332993,16.572924,2.823148")
(COMMAND "POINT" "2.314253,16.718599,2.908859")
(COMMAND "POINT" "2.300086,16.859050,2.990113")
(COMMAND "POINT" "2.290492,16.994277,3.066909")
(COMMAND "POINT" "2.285471,17.124279,3.139248")
(COMMAND "POINT" "2.285023,17.249057,3.207130")
(COMMAND "POINT" "2.289149,17.368611,3.270554")
(COMMAND "POINT" "2.297847,17.482941,3.329521")
(COMMAND "POINT" "2.311118,17.592047,3.384031")
(COMMAND "POINT" "2.328962,17.695928,3.434083")
(COMMAND "POINT" "2.351379,17.794585,3.479678")
(COMMAND "POINT" "2.378370,17.888018,3.520815")
(COMMAND "POINT" "2.409933,17.976227,3.557495")
(COMMAND "POINT" "2.446069,18.059212,3.589718")
(COMMAND "POINT" "2.486778,18.136972,3.617484")
(COMMAND "POINT" "2.532060,18.209509,3.640792")
(COMMAND "POINT" "2.581916,18.276821,3.659642")
(COMMAND "POINT" "2.636344,18.338909,3.674036")
(COMMAND "POINT" "2.695345,18.395773,3.683972")
(COMMAND "POINT" "2.758919,18.447412,3.689450")
(COMMAND "POINT" "2.827067,18.493828,3.690471")
(COMMAND "POINT" "2.899787,18.535019,3.687035")
(COMMAND "POINT" "2.977080,18.570986,3.679142")
(COMMAND "POINT" "3.058946,18.601729,3.666791")
(COMMAND "POINT" "3.145385,18.627248,3.649983")
(COMMAND "POINT" "3.236398,18.647542,3.628717")
(COMMAND "POINT" "3.331983,18.662612,3.602994")
(COMMAND "POINT" "3.432141,18.672458,3.572814")
(COMMAND "POINT" "3.536872,18.677080,3.538176")
(COMMAND "POINT" "3.646177,18.676478,3.499081")
(COMMAND "POINT" "3.760054,18.670652,3.455529")
(COMMAND "POINT" "3.878504,18.659601,3.407519")
(COMMAND "POINT" "4.001527,18.643326,3.355052")
(COMMAND "POINT" "4.129124,18.621827,3.298128")
(COMMAND "POINT" "4.261293,18.595104,3.236746")
(COMMAND "POINT" "4.398035,18.563157,3.170906")
(COMMAND "POINT" "4.539350,18.525985,3.100610")
(COMMAND "POINT" "4.685239,18.483590,3.025856")
(COMMAND "POINT" "4.835700,18.435970,2.946645")
(COMMAND "POINT" "4.990734,18.383126,2.862976")
(COMMAND "POINT" "5.150341,18.325057,2.774850")
(COMMAND "POINT" "5.314522,18.261765,2.682267")
(COMMAND "POINT" "5.483275,18.193248,2.585226")
(COMMAND "POINT" "5.656601,18.119507,2.483728")
(COMMAND "POINT" "5.834501,18.040542,2.377772")
(COMMAND "POINT" "6.016973,17.956353,2.267359")
(COMMAND "POINT" "6.204018,17.866940,2.152489")
(COMMAND "POINT" "6.394777,17.773221,2.034108")
(COMMAND "POINT" "6.584097,17.680708,1.917893")
(COMMAND "POINT" "6.771119,17.590320,1.804791")
(COMMAND "POINT" "6.955842,17.502058,1.694801")
(COMMAND "POINT" "7.138267,17.415920,1.587924")
(COMMAND "POINT" "7.318393,17.331907,1.484159")
(COMMAND "POINT" "7.496221,17.250020,1.383507")
(COMMAND "POINT" "7.671750,17.170257,1.285968")
(COMMAND "POINT" "7.844981,17.092619,1.191541")
(COMMAND "POINT" "8.015914,17.017106,1.100227")
(COMMAND "POINT" "8.184549,16.943718,1.012026")
(COMMAND "POINT" "8.350884,16.872455,0.926937")
(COMMAND "POINT" "8.514922,16.803317,0.844960")
(COMMAND "POINT" "8.676661,16.736304,0.766097")
(COMMAND "POINT" "8.836102,16.671416,0.690346")
(COMMAND "POINT" "8.993244,16.608653,0.617707")
(COMMAND "POINT" "9.148088,16.548015,0.548181")
(COMMAND "POINT" "9.300634,16.489502,0.481768")
(COMMAND "POINT" "9.450881,16.433114,0.418467")
(COMMAND "POINT" "9.598830,16.378850,0.358279")
(COMMAND "POINT" "9.744480,16.326712,0.301204")
(COMMAND "POINT" "9.887832,16.276699,0.247241")
(COMMAND "POINT" "10.028885,16.228811,0.196391")
(COMMAND "POINT" "10.167641,16.183047,0.148653")
(COMMAND "POINT" "10.304097,16.139409,0.104028")
(COMMAND "POINT" "10.438256,16.097895,0.062516")
(COMMAND "POINT" "10.570116,16.058507,0.024116")
(COMMAND "POINT" "10.699677,16.021243,-0.011171")
(COMMAND "POINT" "10.826941,15.986105,-0.043346")
(COMMAND "POINT" "10.951905,15.953091,-0.072408")
(COMMAND "POINT" "11.074572,15.922203,-0.098357")
(COMMAND "POINT" "11.194940,15.893439,-0.121194")
(COMMAND "POINT" "11.313009,15.866800,-0.140918")
(COMMAND "POINT" "11.428781,15.842287,-0.157530")
(COMMAND "POINT" "11.542253,15.819898,-0.171029")
(COMMAND "POINT" "11.653428,15.799634,-0.181415")
(COMMAND "POINT" "11.762304,15.781495,-0.188689")
(COMMAND "POINT" "11.868881,15.765482,-0.192850")
(COMMAND "POINT" "11.973161,15.751593,-0.193898")
(COMMAND "POINT" "12.075141,15.739829,-0.191834")
(COMMAND "POINT" "12.174824,15.730190,-0.186658")
(COMMAND "POINT" "12.272208,15.722676,-0.178368")
(COMMAND "POINT" "12.367294,15.717287,-0.166966")
(COMMAND "POINT" "12.460081,15.714023,-0.152452")
(COMMAND "POINT" "12.550570,15.712884,-0.134825")
(COMMAND "POINT" "12.638760,15.713870,-0.114085")
(COMMAND "POINT" "12.724652,15.716981,-0.090233")
(COMMAND "POINT" "12.808246,15.722216,-0.063268")
(COMMAND "POINT" "12.889541,15.729577,-0.033190")
(COMMAND "POINT" "12.968538,15.739063,0.000000")
(COMMAND "POINT" "2.373590,16.167993,2.609469")
(COMMAND "POINT" "2.334773,16.336748,2.711292")
(COMMAND "POINT" "2.300697,16.500029,2.808534")
(COMMAND "POINT" "2.271361,16.657833,2.901195")
(COMMAND "POINT" "2.246765,16.810163,2.989276")
(COMMAND "POINT" "2.226910,16.957018,3.072776")
(COMMAND "POINT" "2.211795,17.098397,3.151695")
(COMMAND "POINT" "2.201421,17.234301,3.226034")
(COMMAND "POINT" "2.195787,17.364730,3.295792")
(COMMAND "POINT" "2.194893,17.489684,3.360970")
(COMMAND "POINT" "2.198740,17.609163,3.421567")
(COMMAND "POINT" "2.207327,17.723166,3.477584")
(COMMAND "POINT" "2.220655,17.831695,3.529020")
(COMMAND "POINT" "2.238723,17.934748,3.575875")
(COMMAND "POINT" "2.261531,18.032326,3.618150")
(COMMAND "POINT" "2.289080,18.124429,3.655844")
(COMMAND "POINT" "2.321370,18.211056,3.688958")
(COMMAND "POINT" "2.358399,18.292209,3.717491")
(COMMAND "POINT" "2.400170,18.367886,3.741443")
(COMMAND "POINT" "2.446680,18.438088,3.760815")
(COMMAND "POINT" "2.497931,18.502815,3.775606")
(COMMAND "POINT" "2.553923,18.562067,3.785817")
(COMMAND "POINT" "2.614655,18.615844,3.791447")
(COMMAND "POINT" "2.680127,18.664145,3.792496")
(COMMAND "POINT" "2.750339,18.706971,3.788965")
(COMMAND "POINT" "2.825293,18.744322,3.780854")
(COMMAND "POINT" "2.904986,18.776198,3.768161")
(COMMAND "POINT" "2.989420,18.802599,3.750888")
(COMMAND "POINT" "3.078594,18.823524,3.729035")
(COMMAND "POINT" "3.172509,18.838975,3.702601")
(COMMAND "POINT" "3.271164,18.848950,3.671586")
(COMMAND "POINT" "3.374560,18.853450,3.635991")
(COMMAND "POINT" "3.482696,18.852475,3.595815")
(COMMAND "POINT" "3.595572,18.846024,3.551059")
(COMMAND "POINT" "3.713189,18.834099,3.501722")
(COMMAND "POINT" "3.835547,18.816698,3.447804")
(COMMAND "POINT" "3.962644,18.793822,3.389306")
(COMMAND "POINT" "4.094482,18.765471,3.326227")
(COMMAND "POINT" "4.231061,18.731645,3.258568")
(COMMAND "POINT" "4.372380,18.692344,3.186328")
(COMMAND "POINT" "4.518439,18.647567,3.109507")
(COMMAND "POINT" "4.669239,18.597315,3.028106")
(COMMAND "POINT" "4.824779,18.541588,2.942124")
(COMMAND "POINT" "4.985060,18.480386,2.851562")
(COMMAND "POINT" "5.150081,18.413709,2.756419")
(COMMAND "POINT" "5.319842,18.341557,2.656696")
(COMMAND "POINT" "5.494344,18.263929,2.552392")
(COMMAND "POINT" "5.673587,18.180826,2.443507")
(COMMAND "POINT" "5.857569,18.092248,2.330042")
(COMMAND "POINT" "6.046292,17.998195,2.211996")
(COMMAND "POINT" "6.238865,17.899618,2.090342")
(COMMAND "POINT" "6.429944,17.802227,1.970914")
(COMMAND "POINT" "6.618637,17.706972,1.854685")
(COMMAND "POINT" "6.804945,17.613853,1.741654")
(COMMAND "POINT" "6.988869,17.522872,1.631823")
(COMMAND "POINT" "7.170407,17.434027,1.525189")
(COMMAND "POINT" "7.349560,17.347319,1.421755")
(COMMAND "POINT" "7.526328,17.262748,1.321519")
(COMMAND "POINT" "7.700711,17.180313,1.224482")
(COMMAND "POINT" "7.872708,17.100016,1.130643")
(COMMAND "POINT" "8.042321,17.021855,1.040003")
(COMMAND "POINT" "8.209549,16.945830,0.952562")
(COMMAND "POINT" "8.374391,16.871942,0.868320")
(COMMAND "POINT" "8.536848,16.800192,0.787276")
(COMMAND "POINT" "8.696921,16.730577,0.709431")
(COMMAND "POINT" "8.854608,16.663100,0.634784")
(COMMAND "POINT" "9.009910,16.597759,0.563336")
(COMMAND "POINT" "9.162827,16.534555,0.495087")
(COMMAND "POINT" "9.313359,16.473488,0.430036")
(COMMAND "POINT" "9.461506,16.414557,0.368184")
(COMMAND "POINT" "9.607268,16.357763,0.309531")
(COMMAND "POINT" "9.750644,16.303106,0.254076")
(COMMAND "POINT" "9.891636,16.250586,0.201820")
(COMMAND "POINT" "10.030243,16.200202,0.152763")
(COMMAND "POINT" "10.166464,16.151955,0.106904")
(COMMAND "POINT" "10.300300,16.105845,0.064244")
(COMMAND "POINT" "10.431752,16.061871,0.024783")
(COMMAND "POINT" "10.560818,16.020034,-0.011480")
(COMMAND "POINT" "10.687499,15.980334,-0.044544")
(COMMAND "POINT" "10.811795,15.942771,-0.074410")
(COMMAND "POINT" "10.933706,15.907344,-0.101076")
(COMMAND "POINT" "11.053232,15.874054,-0.124544")
(COMMAND "POINT" "11.170372,15.842901,-0.144814")
(COMMAND "POINT" "11.285128,15.813884,-0.161885")
(COMMAND "POINT" "11.397498,15.787004,-0.175757")
(COMMAND "POINT" "11.507484,15.762261,-0.186430")
(COMMAND "POINT" "11.615084,15.739655,-0.193905")
(COMMAND "POINT" "11.720300,15.719185,-0.198181")
(COMMAND "POINT" "11.823130,15.700853,-0.199259")
(COMMAND "POINT" "11.923575,15.684656,-0.197138")
(COMMAND "POINT" "12.021635,15.670597,-0.191818")
(COMMAND "POINT" "12.117310,15.658674,-0.183299")
(COMMAND "POINT" "12.210600,15.648888,-0.171582")
(COMMAND "POINT" "12.301504,15.641239,-0.156666")
(COMMAND "POINT" "12.390024,15.635726,-0.138552")
(COMMAND "POINT" "12.476159,15.632350,-0.117239")
(COMMAND "POINT" "12.559908,15.631111,-0.092727")
(COMMAND "POINT" "12.641272,15.632009,-0.065017")
(COMMAND "POINT" "12.720252,15.635043,-0.034108")
(COMMAND "POINT" "12.796846,15.640214,0.000000")
(COMMAND "POINT" "2.331933,16.230732,2.680423")
(COMMAND "POINT" "2.286581,16.406885,2.785014")
(COMMAND "POINT" "2.246139,16.577311,2.884900")
(COMMAND "POINT" "2.210608,16.742008,2.980080")
(COMMAND "POINT" "2.179988,16.900978,3.070556")
(COMMAND "POINT" "2.154279,17.054221,3.156327")
(COMMAND "POINT" "2.133480,17.201736,3.237392")
(COMMAND "POINT" "2.117592,17.343523,3.313752")
(COMMAND "POINT" "2.106614,17.479583,3.385407")
(COMMAND "POINT" "2.100548,17.609915,3.452357")
(COMMAND "POINT" "2.099391,17.734519,3.514602")
(COMMAND "POINT" "2.103146,17.853396,3.572142")
(COMMAND "POINT" "2.111811,17.966545,3.624976")
(COMMAND "POINT" "2.125387,18.073967,3.673106")
(COMMAND "POINT" "2.143874,18.175661,3.716530")
(COMMAND "POINT" "2.167271,18.271627,3.755249")
(COMMAND "POINT" "2.195579,18.361866,3.789263")
(COMMAND "POINT" "2.228797,18.446377,3.818572")
(COMMAND "POINT" "2.266927,18.525161,3.843176")
(COMMAND "POINT" "2.309967,18.598217,3.863074")
(COMMAND "POINT" "2.357917,18.665545,3.878268")
(COMMAND "POINT" "2.410778,18.727145,3.888756")
(COMMAND "POINT" "2.468550,18.783019,3.894539")
(COMMAND "POINT" "2.531233,18.833164,3.895617")
(COMMAND "POINT" "2.598826,18.877582,3.891990")
(COMMAND "POINT" "2.671330,18.916272,3.883658")
(COMMAND "POINT" "2.748745,18.949235,3.870620")
(COMMAND "POINT" "2.831070,18.976470,3.852878")
(COMMAND "POINT" "2.918306,18.997977,3.830430")
(COMMAND "POINT" "3.010453,19.013757,3.803277")
(COMMAND "POINT" "3.107510,19.023809,3.771419")
(COMMAND "POINT" "3.209478,19.028133,3.734856")
(COMMAND "POINT" "3.316357,19.026730,3.693588")
(COMMAND "POINT" "3.428146,19.019599,3.647615")
(COMMAND "POINT" "3.544846,19.006741,3.596936")
(COMMAND "POINT" "3.666456,18.988155,3.541552")
(COMMAND "POINT" "3.792978,18.963842,3.481464")
(COMMAND "POINT" "3.924410,18.933800,3.416670")
(COMMAND "POINT" "4.060752,18.898032,3.347171")
(COMMAND "POINT" "4.202006,18.856535,3.272966")
(COMMAND "POINT" "4.348170,18.809311,3.194057")
(COMMAND "POINT" "4.499244,18.756360,3.110442")
(COMMAND "POINT" "4.655230,18.697680,3.022123")
(COMMAND "POINT" "4.816126,18.633273,2.929098")
(COMMAND "POINT" "4.981932,18.563139,2.831368")
(COMMAND "POINT" "5.152650,18.487277,2.728933")
(COMMAND "POINT" "5.328278,18.405687,2.621793")
(COMMAND "POINT" "5.508816,18.318370,2.509948")
(COMMAND "POINT" "5.694266,18.225325,2.393397")
(COMMAND "POINT" "5.884626,18.126552,2.272142")
(COMMAND "POINT" "6.078973,18.023036,2.147180")
(COMMAND "POINT" "6.271769,17.920684,2.024505")
(COMMAND "POINT" "6.462091,17.820480,1.905115")
(COMMAND "POINT" "6.649937,17.722423,1.789011")
(COMMAND "POINT" "6.835309,17.626515,1.676193")
(COMMAND "POINT" "7.018207,17.532754,1.566660")
(COMMAND "POINT" "7.198630,17.441142,1.460413")
(COMMAND "POINT" "7.376578,17.351677,1.357452")
(COMMAND "POINT" "7.552051,17.264360,1.257776")
(COMMAND "POINT" "7.725050,17.179192,1.161386")
(COMMAND "POINT" "7.895574,17.096171,1.068282")
(COMMAND "POINT" "8.063623,17.015298,0.978463")
(COMMAND "POINT" "8.229198,16.936573,0.891930")
(COMMAND "POINT" "8.392298,16.859996,0.808682")
(COMMAND "POINT" "8.552923,16.785567,0.728720")
(COMMAND "POINT" "8.711074,16.713285,0.652044")
(COMMAND "POINT" "8.866750,16.643152,0.578653")
(COMMAND "POINT" "9.019951,16.575167,0.508548")
(COMMAND "POINT" "9.170678,16.509329,0.441729")
(COMMAND "POINT" "9.318930,16.445640,0.378195")
(COMMAND "POINT" "9.464707,16.384098,0.317947")
(COMMAND "POINT" "9.608010,16.324704,0.260985")
(COMMAND "POINT" "9.748838,16.267459,0.207308")
(COMMAND "POINT" "9.887191,16.212361,0.156916")
(COMMAND "POINT" "10.023070,16.159411,0.109811")
(COMMAND "POINT" "10.156474,16.108609,0.065991")
(COMMAND "POINT" "10.287403,16.059955,0.025457")
(COMMAND "POINT" "10.415858,16.013449,-0.011792")
(COMMAND "POINT" "10.541838,15.969091,-0.045755")
(COMMAND "POINT" "10.665343,15.926881,-0.076433")
(COMMAND "POINT" "10.786374,15.886819,-0.103825")
(COMMAND "POINT" "10.904930,15.848904,-0.127931")
(COMMAND "POINT" "11.021012,15.813138,-0.148751")
(COMMAND "POINT" "11.134618,15.779519,-0.166286")
(COMMAND "POINT" "11.245750,15.748049,-0.180536")
(COMMAND "POINT" "11.354408,15.718726,-0.191499")
(COMMAND "POINT" "11.460590,15.691551,-0.199177")
(COMMAND "POINT" "11.564298,15.666525,-0.203570")
(COMMAND "POINT" "11.665532,15.643646,-0.204677")
(COMMAND "POINT" "11.764290,15.622915,-0.202498")
(COMMAND "POINT" "11.860574,15.604332,-0.197033")
(COMMAND "POINT" "11.954384,15.587897,-0.188283")
(COMMAND "POINT" "12.045718,15.573610,-0.176248")
(COMMAND "POINT" "12.134578,15.561471,-0.160926")
(COMMAND "POINT" "12.220964,15.551479,-0.142319")
(COMMAND "POINT" "12.304874,15.543636,-0.120427")
(COMMAND "POINT" "12.386310,15.537941,-0.095248")
(COMMAND "POINT" "12.465272,15.534393,-0.066785")
(COMMAND "POINT" "12.541759,15.532994,-0.035035")
(COMMAND "POINT" "12.615771,15.533742,0.000000")
(COMMAND "POINT" "2.291677,16.292772,2.752130")
(COMMAND "POINT" "2.239613,16.476312,2.859519")
(COMMAND "POINT" "2.192632,16.653871,2.962077")
(COMMAND "POINT" "2.150735,16.825449,3.059804")
(COMMAND "POINT" "2.113922,16.991045,3.152700")
(COMMAND "POINT" "2.082192,17.150660,3.240765")
(COMMAND "POINT" "2.055547,17.304293,3.323999")
(COMMAND "POINT" "2.033985,17.451944,3.402402")
(COMMAND "POINT" "2.017507,17.593614,3.475974")
(COMMAND "POINT" "2.006112,17.729303,3.544715")
(COMMAND "POINT" "1.999802,17.859010,3.608625")
(COMMAND "POINT" "1.998575,17.982736,3.667704")
(COMMAND "POINT" "2.002432,18.100480,3.721952")
(COMMAND "POINT" "2.011372,18.212242,3.771369")
(COMMAND "POINT" "2.025397,18.318023,3.815955")
(COMMAND "POINT" "2.044505,18.417823,3.855710")
(COMMAND "POINT" "2.068697,18.511641,3.890634")
(COMMAND "POINT" "2.097972,18.599477,3.920727")
(COMMAND "POINT" "2.132332,18.681332,3.945989")
(COMMAND "POINT" "2.171775,18.757206,3.966420")
(COMMAND "POINT" "2.216302,18.827098,3.982020")
(COMMAND "POINT" "2.265913,18.891008,3.992789")
(COMMAND "POINT" "2.320607,18.948937,3.998726")
(COMMAND "POINT" "2.380385,19.000885,3.999833")
(COMMAND "POINT" "2.445247,19.046851,3.996109")
(COMMAND "POINT" "2.515193,19.086835,3.987554")
(COMMAND "POINT" "2.590222,19.120838,3.974168")
(COMMAND "POINT" "2.670336,19.148860,3.955951")
(COMMAND "POINT" "2.755533,19.170900,3.932902")
(COMMAND "POINT" "2.845813,19.186958,3.905023")
(COMMAND "POINT" "2.941178,19.197035,3.872313")
(COMMAND "POINT" "3.041626,19.201131,3.834772")
(COMMAND "POINT" "3.147158,19.199245,3.792399")
(COMMAND "POINT" "3.257774,19.191377,3.745196")
(COMMAND "POINT" "3.373474,19.177528,3.693162")
(COMMAND "POINT" "3.494257,19.157697,3.636297")
(COMMAND "POINT" "3.620124,19.131885,3.574600")
(COMMAND "POINT" "3.751075,19.100092,3.508073")
(COMMAND "POINT" "3.887110,19.062317,3.436715")
(COMMAND "POINT" "4.028228,19.018560,3.360525")
(COMMAND "POINT" "4.174430,18.968822,3.279505")
(COMMAND "POINT" "4.325716,18.913102,3.193654")
(COMMAND "POINT" "4.482086,18.851401,3.102971")
(COMMAND "POINT" "4.643539,18.783719,3.007458")
(COMMAND "POINT" "4.810076,18.710054,2.907113")
(COMMAND "POINT" "4.981697,18.630409,2.801938")
(COMMAND "POINT" "5.158402,18.544782,2.691932")
(COMMAND "POINT" "5.340190,18.453173,2.577094")
(COMMAND "POINT" "5.527062,18.355583,2.457426")
(COMMAND "POINT" "5.719018,18.252011,2.332926")
(COMMAND "POINT" "5.915102,18.143476,2.204621")
(COMMAND "POINT" "6.109574,18.036081,2.078664")
(COMMAND "POINT" "6.301480,17.930845,1.956081")
(COMMAND "POINT" "6.490818,17.827768,1.836871")
(COMMAND "POINT" "6.677589,17.726849,1.721035")
(COMMAND "POINT" "6.861793,17.628089,1.608572")
(COMMAND "POINT" "7.043430,17.531487,1.499483")
(COMMAND "POINT" "7.222500,17.437044,1.393767")
(COMMAND "POINT" "7.399003,17.344760,1.291425")
(COMMAND "POINT" "7.572938,17.254634,1.192456")
(COMMAND "POINT" "7.744306,17.166667,1.096861")
(COMMAND "POINT" "7.913108,17.080858,1.004639")
(COMMAND "POINT" "8.079342,16.997208,0.915791")
(COMMAND "POINT" "8.243009,16.915717,0.830316")
(COMMAND "POINT" "8.404109,16.836384,0.748215")
(COMMAND "POINT" "8.562641,16.759209,0.669488")
(COMMAND "POINT" "8.718607,16.684194,0.594134")
(COMMAND "POINT" "8.872006,16.611337,0.522153")
(COMMAND "POINT" "9.022837,16.540638,0.453546")
(COMMAND "POINT" "9.171101,16.472098,0.388313")
(COMMAND "POINT" "9.316798,16.405717,0.326453")
(COMMAND "POINT" "9.459928,16.341494,0.267967")
(COMMAND "POINT" "9.600491,16.279430,0.212854")
(COMMAND "POINT" "9.738487,16.219525,0.161114")
(COMMAND "POINT" "9.873915,16.161778,0.112749")
(COMMAND "POINT" "10.006777,16.106189,0.067756")
(COMMAND "POINT" "10.137071,16.052760,0.026138")
(COMMAND "POINT" "10.264798,16.001488,-0.012108")
(COMMAND "POINT" "10.389958,15.952376,-0.046979")
(COMMAND "POINT" "10.512551,15.905422,-0.078478")
(COMMAND "POINT" "10.632577,15.860626,-0.106602")
(COMMAND "POINT" "10.750035,15.817990,-0.131353")
(COMMAND "POINT" "10.864927,15.777511,-0.152731")
(COMMAND "POINT" "10.977251,15.739192,-0.170735")
(COMMAND "POINT" "11.087009,15.703031,-0.185365")
(COMMAND "POINT" "11.194199,15.669028,-0.196622")
(COMMAND "POINT" "11.298822,15.637185,-0.204506")
(COMMAND "POINT" "11.400878,15.607499,-0.209016")
(COMMAND "POINT" "11.500366,15.579973,-0.210152")
(COMMAND "POINT" "11.597288,15.554605,-0.207915")
(COMMAND "POINT" "11.691642,15.531395,-0.202305")
(COMMAND "POINT" "11.783430,15.510344,-0.193320")
(COMMAND "POINT" "11.872650,15.491452,-0.180963")
(COMMAND "POINT" "11.959303,15.474718,-0.165231")
(COMMAND "POINT" "12.043389,15.460143,-0.146127")
(COMMAND "POINT" "12.124908,15.447727,-0.123648")
(COMMAND "POINT" "12.203859,15.437469,-0.097797")
(COMMAND "POINT" "12.280244,15.429370,-0.068571")
(COMMAND "POINT" "12.354061,15.423429,-0.035972")
(COMMAND "POINT" "12.425312,15.419647,0.000000")
(COMMAND "POINT" "2.252824,16.354112,2.824591")
(COMMAND "POINT" "2.193870,16.545030,2.934807")
(COMMAND "POINT" "2.140176,16.729711,3.040066")
(COMMAND "POINT" "2.091741,16.908155,3.140366")
(COMMAND "POINT" "2.048566,17.080363,3.235708")
(COMMAND "POINT" "2.010651,17.246334,3.326091")
(COMMAND "POINT" "1.977995,17.406068,3.411517")
(COMMAND "POINT" "1.950600,17.559565,3.491984")
(COMMAND "POINT" "1.928463,17.706825,3.567493")
(COMMAND "POINT" "1.911587,17.847849,3.638044")
(COMMAND "POINT" "1.899970,17.982635,3.703637")
(COMMAND "POINT" "1.893613,18.111185,3.764271")
(COMMAND "POINT" "1.892516,18.233498,3.819948")
(COMMAND "POINT" "1.896678,18.349574,3.870666")
(COMMAND "POINT" "1.906100,18.459413,3.916426")
(COMMAND "POINT" "1.920782,18.563015,3.957227")
(COMMAND "POINT" "1.940723,18.660381,3.993071")
(COMMAND "POINT" "1.965924,18.751509,4.023956")
(COMMAND "POINT" "1.996385,18.836401,4.049883")
(COMMAND "POINT" "2.032105,18.915056,4.070852")
(COMMAND "POINT" "2.073085,18.987474,4.086862")
(COMMAND "POINT" "2.119325,19.053656,4.097915")
(COMMAND "POINT" "2.170824,19.113600,4.104009")
(COMMAND "POINT" "2.227583,19.167308,4.105145")
(COMMAND "POINT" "2.289602,19.214778,4.101323")
(COMMAND "POINT" "2.356881,19.256012,4.092542")
(COMMAND "POINT" "2.429419,19.291009,4.078804")
(COMMAND "POINT" "2.507217,19.319769,4.060107")
(COMMAND "POINT" "2.590274,19.342293,4.036452")
(COMMAND "POINT" "2.678591,19.358579,4.007839")
(COMMAND "POINT" "2.772168,19.368629,3.974267")
(COMMAND "POINT" "2.871005,19.372442,3.935737")
(COMMAND "POINT" "2.975101,19.370018,3.892250")
(COMMAND "POINT" "3.084457,19.361357,3.843803")
(COMMAND "POINT" "3.199073,19.346459,3.790399")
(COMMAND "POINT" "3.318948,19.325325,3.732037")
(COMMAND "POINT" "3.444083,19.297953,3.668716")
(COMMAND "POINT" "3.574478,19.264345,3.600437")
(COMMAND "POINT" "3.710132,19.224500,3.527200")
(COMMAND "POINT" "3.851046,19.178418,3.449005")
(COMMAND "POINT" "3.997220,19.126099,3.365851")
(COMMAND "POINT" "4.148654,19.067544,3.277739")
(COMMAND "POINT" "4.305347,19.002751,3.184669")
(COMMAND "POINT" "4.467300,18.931722,3.086641")
(COMMAND "POINT" "4.634512,18.854456,2.983655")
(COMMAND "POINT" "4.806984,18.770953,2.875710")
(COMMAND "POINT" "4.984716,18.681213,2.762808")
(COMMAND "POINT" "5.167708,18.585236,2.644947")
(COMMAND "POINT" "5.355959,18.483023,2.522127")
(COMMAND "POINT" "5.549470,18.374572,2.394350")
(COMMAND "POINT" "5.747250,18.260936,2.262667")
(COMMAND "POINT" "5.943358,18.148417,2.133394")
(COMMAND "POINT" "6.136804,18.038067,2.007583")
(COMMAND "POINT" "6.327587,17.929886,1.885234")
(COMMAND "POINT" "6.515708,17.823874,1.766348")
(COMMAND "POINT" "6.701166,17.720030,1.650924")
(COMMAND "POINT" "6.883961,17.618355,1.538963")
(COMMAND "POINT" "7.064095,17.518849,1.430463")
(COMMAND "POINT" "7.241565,17.421511,1.325427")
(COMMAND "POINT" "7.416374,17.326343,1.223852")
(COMMAND "POINT" "7.588519,17.233342,1.125740")
(COMMAND "POINT" "7.758003,17.142511,1.031090")
(COMMAND "POINT" "7.924824,17.053848,0.939903")
(COMMAND "POINT" "8.088982,16.967354,0.852178")
(COMMAND "POINT" "8.250478,16.883029,0.767915")
(COMMAND "POINT" "8.409311,16.800872,0.687115")
(COMMAND "POINT" "8.565482,16.720884,0.609777")
(COMMAND "POINT" "8.718990,16.643065,0.535901")
(COMMAND "POINT" "8.869836,16.567415,0.465488")
(COMMAND "POINT" "9.018020,16.493933,0.398537")
(COMMAND "POINT" "9.163541,16.422620,0.335048")
(COMMAND "POINT" "9.306399,16.353475,0.275022")
(COMMAND "POINT" "9.446595,16.286500,0.218458")
(COMMAND "POINT" "9.584129,16.221693,0.165356")
(COMMAND "POINT" "9.719000,16.159055,0.115717")
(COMMAND "POINT" "9.851208,16.098585,0.069540")
(COMMAND "POINT" "9.980754,16.040284,0.026826")
(COMMAND "POINT" "10.107638,15.984152,-0.012426")
(COMMAND "POINT" "10.231859,15.930189,-0.048216")
(COMMAND "POINT" "10.353418,15.878394,-0.080544")
(COMMAND "POINT" "10.472314,15.828768,-0.109409")
(COMMAND "POINT" "10.588548,15.781311,-0.134812")
(COMMAND "POINT" "10.702119,15.736022,-0.156752")
(COMMAND "POINT" "10.813027,15.692902,-0.175230")
(COMMAND "POINT" "10.921274,15.651951,-0.190246")
(COMMAND "POINT" "11.026857,15.613168,-0.201799")
(COMMAND "POINT" "11.129779,15.576555,-0.209890")
(COMMAND "POINT" "11.230037,15.542110,-0.214519")
(COMMAND "POINT" "11.327634,15.509833,-0.215685")
(COMMAND "POINT" "11.422568,15.479726,-0.213389")
(COMMAND "POINT" "11.514839,15.451787,-0.207631")
(COMMAND "POINT" "11.604448,15.426016,-0.198410")
(COMMAND "POINT" "11.691394,15.402415,-0.185727")
(COMMAND "POINT" "11.775678,15.380982,-0.169582")
(COMMAND "POINT" "11.857299,15.361718,-0.149974")
(COMMAND "POINT" "11.936258,15.344622,-0.126904")
(COMMAND "POINT" "12.012555,15.329696,-0.100371")
(COMMAND "POINT" "12.086189,15.316938,-0.070377")
(COMMAND "POINT" "12.157160,15.306348,-0.036920")
(COMMAND "POINT" "12.225469,15.297928,0.000000")
(COMMAND "POINT" "2.215372,16.414752,2.897805")
(COMMAND "POINT" "2.149352,16.613037,3.010879")
(COMMAND "POINT" "2.088770,16.804829,3.118866")
(COMMAND "POINT" "2.033626,16.990128,3.221766")
(COMMAND "POINT" "1.983921,17.168932,3.319579")
(COMMAND "POINT" "1.939654,17.341244,3.412305")
(COMMAND "POINT" "1.900826,17.507061,3.499945")
(COMMAND "POINT" "1.867436,17.666385,3.582498")
(COMMAND "POINT" "1.839485,17.819215,3.659964")
(COMMAND "POINT" "1.816972,17.965552,3.732344")
(COMMAND "POINT" "1.799897,18.105395,3.799637")
(COMMAND "POINT" "1.788261,18.238744,3.861843")
(COMMAND "POINT" "1.782064,18.365599,3.918963")
(COMMAND "POINT" "1.781305,18.485962,3.970995")
(COMMAND "POINT" "1.785984,18.599830,4.017941")
(COMMAND "POINT" "1.796102,18.707205,4.059800")
(COMMAND "POINT" "1.811658,18.808086,4.096573")
(COMMAND "POINT" "1.832652,18.902473,4.128259")
(COMMAND "POINT" "1.859086,18.990367,4.154858")
(COMMAND "POINT" "1.890957,19.071767,4.176370")
(COMMAND "POINT" "1.928267,19.146674,4.192796")
(COMMAND "POINT" "1.971015,19.215087,4.204135")
(COMMAND "POINT" "2.019202,19.277006,4.210387")
(COMMAND "POINT" "2.072828,19.332432,4.211552")
(COMMAND "POINT" "2.131891,19.381364,4.207631")
(COMMAND "POINT" "2.196394,19.423803,4.198623")
(COMMAND "POINT" "2.266334,19.459747,4.184528")
(COMMAND "POINT" "2.341713,19.489198,4.165347")
(COMMAND "POINT" "2.422531,19.512156,4.141079")
(COMMAND "POINT" "2.508787,19.528620,4.111724")
(COMMAND "POINT" "2.600481,19.538590,4.077282")
(COMMAND "POINT" "2.697614,19.542067,4.037754")
(COMMAND "POINT" "2.800185,19.539050,3.993139")
(COMMAND "POINT" "2.908195,19.529539,3.943437")
(COMMAND "POINT" "3.021643,19.513535,3.888648")
(COMMAND "POINT" "3.140530,19.491037,3.828773")
(COMMAND "POINT" "3.264855,19.462046,3.763811")
(COMMAND "POINT" "3.394619,19.426560,3.693762")
(COMMAND "POINT" "3.529821,19.384582,3.618627")
(COMMAND "POINT" "3.670461,19.336109,3.538405")
(COMMAND "POINT" "3.816540,19.281143,3.453096")
(COMMAND "POINT" "3.968057,19.219683,3.362700")
(COMMAND "POINT" "4.125013,19.151730,3.267218")
(COMMAND "POINT" "4.287407,19.077283,3.166648")
(COMMAND "POINT" "4.455240,18.996343,3.060993")
(COMMAND "POINT" "4.628511,18.908908,2.950250")
(COMMAND "POINT" "4.807221,18.814980,2.834421")
(COMMAND "POINT" "4.991369,18.714559,2.713505")
(COMMAND "POINT" "5.180955,18.607644,2.587502")
(COMMAND "POINT" "5.375980,18.494235,2.456413")
(COMMAND "POINT" "5.575419,18.375417,2.321316")
(COMMAND "POINT" "5.773121,18.257693,2.188692")
(COMMAND "POINT" "5.968063,18.142147,2.059620")
(COMMAND "POINT" "6.160244,18.028779,1.934100")
(COMMAND "POINT" "6.349665,17.917590,1.812133")
(COMMAND "POINT" "6.536325,17.808579,1.693717")
(COMMAND "POINT" "6.720224,17.701746,1.578853")
(COMMAND "POINT" "6.901362,17.597092,1.467542")
(COMMAND "POINT" "7.079740,17.494615,1.359782")
(COMMAND "POINT" "7.255357,17.394318,1.255575")
(COMMAND "POINT" "7.428213,17.296198,1.154920")
(COMMAND "POINT" "7.598308,17.200257,1.057817")
(COMMAND "POINT" "7.765643,17.106493,0.964266")
(COMMAND "POINT" "7.930217,17.014909,0.874267")
(COMMAND "POINT" "8.092030,16.925502,0.787820")
(COMMAND "POINT" "8.251083,16.838274,0.704925")
(COMMAND "POINT" "8.407375,16.753224,0.625582")
(COMMAND "POINT" "8.560906,16.670352,0.549792")
(COMMAND "POINT" "8.711676,16.589659,0.477553")
(COMMAND "POINT" "8.859686,16.511143,0.408867")
(COMMAND "POINT" "9.004935,16.434807,0.343733")
(COMMAND "POINT" "9.147423,16.360648,0.282151")
(COMMAND "POINT" "9.287151,16.288668,0.224120")
(COMMAND "POINT" "9.424118,16.218866,0.169642")
(COMMAND "POINT" "9.558324,16.151242,0.118717")
(COMMAND "POINT" "9.689769,16.085796,0.071343")
(COMMAND "POINT" "9.818454,16.022529,0.027521")
(COMMAND "POINT" "9.944378,15.961440,-0.012749")
(COMMAND "POINT" "10.067541,15.902529,-0.049466")
(COMMAND "POINT" "10.187944,15.845797,-0.082632")
(COMMAND "POINT" "10.305585,15.791243,-0.112245")
(COMMAND "POINT" "10.420466,15.738867,-0.138306")
(COMMAND "POINT" "10.532587,15.688669,-0.160815")
(COMMAND "POINT" "10.641946,15.640650,-0.179772")
(COMMAND "POINT" "10.748545,15.594809,-0.195177")
(COMMAND "POINT" "10.852384,15.551146,-0.207030")
(COMMAND "POINT" "10.953461,15.509661,-0.215331")
(COMMAND "POINT" "11.051778,15.470355,-0.220079")
(COMMAND "POINT" "11.147334,15.433227,-0.221276")
(COMMAND "POINT" "11.240129,15.398278,-0.218921")
(COMMAND "POINT" "11.330164,15.365506,-0.213013")
(COMMAND "POINT" "11.417438,15.334913,-0.203553")
(COMMAND "POINT" "11.501951,15.306498,-0.190541")
(COMMAND "POINT" "11.583703,15.280261,-0.173977")
(COMMAND "POINT" "11.662695,15.256203,-0.153861")
(COMMAND "POINT" "11.738926,15.234323,-0.130193")
(COMMAND "POINT" "11.812397,15.214621,-0.102973")
(COMMAND "POINT" "11.883106,15.197098,-0.072201")
(COMMAND "POINT" "11.951055,15.181753,-0.037876")
(COMMAND "POINT" "12.016243,15.168586,0.000000")
(COMMAND "POINT" "2.179323,16.474692,2.971774")
(COMMAND "POINT" "2.106059,16.680335,3.087734")
(COMMAND "POINT" "2.038415,16.879227,3.198477")
(COMMAND "POINT" "1.976391,17.071366,3.304003")
(COMMAND "POINT" "1.919987,17.256753,3.404313")
(COMMAND "POINT" "1.869203,17.435389,3.499407")
(COMMAND "POINT" "1.824039,17.607272,3.589284")
(COMMAND "POINT" "1.784495,17.772404,3.673944")
(COMMAND "POINT" "1.750571,17.930784,3.753388")
(COMMAND "POINT" "1.722267,18.082412,3.827615")
(COMMAND "POINT" "1.699583,18.227288,3.896625")
(COMMAND "POINT" "1.682519,18.365413,3.960419")
(COMMAND "POINT" "1.671076,18.496785,4.018997")
(COMMAND "POINT" "1.665252,18.621406,4.072358")
(COMMAND "POINT" "1.665048,18.739274,4.120502")
(COMMAND "POINT" "1.670465,18.850391,4.163430")
(COMMAND "POINT" "1.681501,18.954756,4.201141")
(COMMAND "POINT" "1.698158,19.052369,4.233636")
(COMMAND "POINT" "1.720434,19.143230,4.260914")
(COMMAND "POINT" "1.748331,19.227340,4.282975")
(COMMAND "POINT" "1.781848,19.304697,4.299820")
(COMMAND "POINT" "1.820984,19.375303,4.311448")
(COMMAND "POINT" "1.865741,19.439157,4.317860")
(COMMAND "POINT" "1.916118,19.496258,4.319055")
(COMMAND "POINT" "1.972115,19.546608,4.315034")
(COMMAND "POINT" "2.033732,19.590206,4.305796")
(COMMAND "POINT" "2.100968,19.627053,4.291341")
(COMMAND "POINT" "2.173825,19.657147,4.271670")
(COMMAND "POINT" "2.252302,19.680490,4.246783")
(COMMAND "POINT" "2.336399,19.697080,4.216678")
(COMMAND "POINT" "2.426117,19.706919,4.181358")
(COMMAND "POINT" "2.521454,19.710006,4.140820")
(COMMAND "POINT" "2.622411,19.706341,4.095066")
(COMMAND "POINT" "2.728988,19.695924,4.044096")
(COMMAND "POINT" "2.841185,19.678755,3.987909")
(COMMAND "POINT" "2.959003,19.654835,3.926505")
(COMMAND "POINT" "3.082440,19.624162,3.859885")
(COMMAND "POINT" "3.211497,19.586738,3.788048")
(COMMAND "POINT" "3.346175,19.542562,3.710995")
(COMMAND "POINT" "3.486472,19.491634,3.628725")
(COMMAND "POINT" "3.632390,19.433954,3.541238")
(COMMAND "POINT" "3.783928,19.369522,3.448535")
(COMMAND "POINT" "3.941085,19.298338,3.350616")
(COMMAND "POINT" "4.103863,19.220403,3.247479")
(COMMAND "POINT" "4.272261,19.135715,3.139127")
(COMMAND "POINT" "4.446278,19.044276,3.025557")
(COMMAND "POINT" "4.625916,18.946085,2.906771")
(COMMAND "POINT" "4.811174,18.841142,2.782769")
(COMMAND "POINT" "5.002052,18.729447,2.653550")
(COMMAND "POINT" "5.198550,18.611000,2.519114")
(COMMAND "POINT" "5.399608,18.486919,2.380570")
(COMMAND "POINT" "5.598864,18.363907,2.244560")
(COMMAND "POINT" "5.795258,18.243083,2.112194")
(COMMAND "POINT" "5.988790,18.124446,1.983470")
(COMMAND "POINT" "6.179461,18.007997,1.858389")
(COMMAND "POINT" "6.367270,17.893735,1.736950")
(COMMAND "POINT" "6.552217,17.781660,1.619155")
(COMMAND "POINT" "6.734302,17.671772,1.505002")
(COMMAND "POINT" "6.913525,17.564072,1.394492")
(COMMAND "POINT" "7.089887,17.458559,1.287624")
(COMMAND "POINT" "7.263386,17.355233,1.184400")
(COMMAND "POINT" "7.434024,17.254095,1.084818")
(COMMAND "POINT" "7.601800,17.155144,0.988879")
(COMMAND "POINT" "7.766714,17.058380,0.896583")
(COMMAND "POINT" "7.928766,16.963803,0.807929")
(COMMAND "POINT" "8.087956,16.871414,0.722919")
(COMMAND "POINT" "8.244285,16.781212,0.641551")
(COMMAND "POINT" "8.397752,16.693197,0.563826")
(COMMAND "POINT" "8.548356,16.607370,0.489743")
(COMMAND "POINT" "8.696099,16.523730,0.419304")
(COMMAND "POINT" "8.840981,16.442277,0.352507")
(COMMAND "POINT" "8.983000,16.363012,0.289353")
(COMMAND "POINT" "9.122157,16.285934,0.229841")
(COMMAND "POINT" "9.258453,16.211043,0.173973")
(COMMAND "POINT" "9.391887,16.138339,0.121747")
(COMMAND "POINT" "9.522459,16.067823,0.073164")
(COMMAND "POINT" "9.650169,15.999494,0.028224")
(COMMAND "POINT" "9.775017,15.933352,-0.013074")
(COMMAND "POINT" "9.897004,15.869398,-0.050729")
(COMMAND "POINT" "10.016128,15.807631,-0.084741")
(COMMAND "POINT" "10.132391,15.748051,-0.115110")
(COMMAND "POINT" "10.245792,15.690658,-0.141836")
(COMMAND "POINT" "10.356331,15.635453,-0.164920")
(COMMAND "POINT" "10.464008,15.582435,-0.184361")
(COMMAND "POINT" "10.568824,15.531604,-0.200159")
(COMMAND "POINT" "10.670777,15.482961,-0.212315")
(COMMAND "POINT" "10.769869,15.436505,-0.220827")
(COMMAND "POINT" "10.866099,15.392236,-0.225697")
(COMMAND "POINT" "10.959467,15.350155,-0.226924")
(COMMAND "POINT" "11.049973,15.310261,-0.224509")
(COMMAND "POINT" "11.137617,15.272554,-0.218450")
(COMMAND "POINT" "11.222400,15.237034,-0.208749")
(COMMAND "POINT" "11.304321,15.203702,-0.195405")
(COMMAND "POINT" "11.383379,15.172557,-0.178418")
(COMMAND "POINT" "11.459576,15.143599,-0.157789")
(COMMAND "POINT" "11.532912,15.116829,-0.133517")
(COMMAND "POINT" "11.603385,15.092246,-0.105602")
(COMMAND "POINT" "11.670996,15.069850,-0.074044")
(COMMAND "POINT" "11.735746,15.049641,-0.038843")
(COMMAND "POINT" "11.797634,15.031620,0.000000")
(COMMAND "POINT" "2.144676,16.533933,3.046496")
(COMMAND "POINT" "2.063991,16.746924,3.165372")
(COMMAND "POINT" "1.989110,16.952902,3.278900")
(COMMAND "POINT" "1.920034,17.151870,3.387079")
(COMMAND "POINT" "1.856763,17.343825,3.489912")
(COMMAND "POINT" "1.799296,17.528769,3.587396")
(COMMAND "POINT" "1.747633,17.706702,3.679533")
(COMMAND "POINT" "1.701775,17.877623,3.766322")
(COMMAND "POINT" "1.661721,18.041532,3.847763")
(COMMAND "POINT" "1.627472,18.198430,3.923857")
(COMMAND "POINT" "1.599027,18.348316,3.994602")
(COMMAND "POINT" "1.576387,18.491191,4.060000")
(COMMAND "POINT" "1.559551,18.627054,4.120051")
(COMMAND "POINT" "1.548520,18.755906,4.174753")
(COMMAND "POINT" "1.543293,18.877746,4.224108")
(COMMAND "POINT" "1.543871,18.992575,4.268115")
(COMMAND "POINT" "1.550253,19.100392,4.306775")
(COMMAND "POINT" "1.562440,19.201197,4.340086")
(COMMAND "POINT" "1.580431,19.294991,4.368050")
(COMMAND "POINT" "1.604227,19.381773,4.390666")
(COMMAND "POINT" "1.633827,19.461544,4.407935")
(COMMAND "POINT" "1.669231,19.534303,4.419856")
(COMMAND "POINT" "1.710440,19.600050,4.426429")
(COMMAND "POINT" "1.757454,19.658787,4.427654")
(COMMAND "POINT" "1.810272,19.710511,4.423531")
(COMMAND "POINT" "1.868895,19.755224,4.414061")
(COMMAND "POINT" "1.933322,19.792925,4.399243")
(COMMAND "POINT" "2.003553,19.823615,4.379077")
(COMMAND "POINT" "2.079589,19.847293,4.353564")
(COMMAND "POINT" "2.161429,19.863960,4.322703")
(COMMAND "POINT" "2.249074,19.873615,4.286494")
(COMMAND "POINT" "2.342524,19.876259,4.244937")
(COMMAND "POINT" "2.441777,19.871891,4.198033")
(COMMAND "POINT" "2.546836,19.860511,4.145781")
(COMMAND "POINT" "2.657699,19.842120,4.088181")
(COMMAND "POINT" "2.774366,19.816717,4.025233")
(COMMAND "POINT" "2.896838,19.784303,3.956938")
(COMMAND "POINT" "3.025114,19.744877,3.883295")
(COMMAND "POINT" "3.159195,19.698440,3.804304")
(COMMAND "POINT" "3.299080,19.644991,3.719966")
(COMMAND "POINT" "3.444770,19.584531,3.630279")
(COMMAND "POINT" "3.596264,19.517059,3.535245")
(COMMAND "POINT" "3.753562,19.442575,3.434864")
(COMMAND "POINT" "3.916666,19.361080,3.329134")
(COMMAND "POINT" "4.085573,19.272573,3.218057")
(COMMAND "POINT" "4.260285,19.177055,3.101632")
(COMMAND "POINT" "4.440802,19.074525,2.979859")
(COMMAND "POINT" "4.627123,18.964984,2.852739")
(COMMAND "POINT" "4.819248,18.848431,2.720271")
(COMMAND "POINT" "5.017178,18.724867,2.582455")
(COMMAND "POINT" "5.219817,18.595441,2.440427")
(COMMAND "POINT" "5.420585,18.467061,2.300998")
(COMMAND "POINT" "5.618388,18.340877,2.165303")
(COMMAND "POINT" "5.813225,18.216888,2.033342")
(COMMAND "POINT" "6.005096,18.095095,1.905116")
(COMMAND "POINT" "6.194001,17.975498,1.780624")
(COMMAND "POINT" "6.379941,17.858096,1.659867")
(COMMAND "POINT" "6.562914,17.742891,1.542844")
(COMMAND "POINT" "6.742922,17.629881,1.429555")
(COMMAND "POINT" "6.919964,17.519067,1.320001")
(COMMAND "POINT" "7.094040,17.410448,1.214181")
(COMMAND "POINT" "7.265150,17.304026,1.112095")
(COMMAND "POINT" "7.433294,17.199799,1.013744")
(COMMAND "POINT" "7.598473,17.097768,0.919127")
(COMMAND "POINT" "7.760685,16.997932,0.828244")
(COMMAND "POINT" "7.919932,16.900293,0.741096")
(COMMAND "POINT" "8.076213,16.804849,0.657682")
(COMMAND "POINT" "8.229528,16.711601,0.578003")
(COMMAND "POINT" "8.379877,16.620549,0.502057")
(COMMAND "POINT" "8.527260,16.531693,0.429847")
(COMMAND "POINT" "8.671678,16.445032,0.361370")
(COMMAND "POINT" "8.813130,16.360567,0.296628")
(COMMAND "POINT" "8.951615,16.278298,0.235620")
(COMMAND "POINT" "9.087135,16.198224,0.178347")
(COMMAND "POINT" "9.219689,16.120347,0.124808")
(COMMAND "POINT" "9.349278,16.044665,0.075003")
(COMMAND "POINT" "9.475900,15.971179,0.028933")
(COMMAND "POINT" "9.599557,15.899889,-0.013403")
(COMMAND "POINT" "9.720247,15.830794,-0.052004")
(COMMAND "POINT" "9.837972,15.763895,-0.086871")
(COMMAND "POINT" "9.952731,15.699192,-0.118004")
(COMMAND "POINT" "10.064524,15.636685,-0.145403")
(COMMAND "POINT" "10.173352,15.576374,-0.169067")
(COMMAND "POINT" "10.279213,15.518258,-0.188997")
(COMMAND "POINT" "10.382109,15.462338,-0.205192")
(COMMAND "POINT" "10.482038,15.408614,-0.217653")
(COMMAND "POINT" "10.579002,15.357085,-0.226380")
(COMMAND "POINT" "10.673000,15.307753,-0.231372")
(COMMAND "POINT" "10.764033,15.260616,-0.232630")
(COMMAND "POINT" "10.852099,15.215675,-0.230154")
(COMMAND "POINT" "10.937199,15.172930,-0.223943")
(COMMAND "POINT" "11.019334,15.132380,-0.213998")
(COMMAND "POINT" "11.098503,15.094026,-0.200318")
(COMMAND "POINT" "11.174706,15.057868,-0.182905")
(COMMAND "POINT" "11.247943,15.023906,-0.161756")
(COMMAND "POINT" "11.318214,14.992139,-0.136874")
(COMMAND "POINT" "11.385520,14.962569,-0.108257")
(COMMAND "POINT" "11.449859,14.935194,-0.075906")
(COMMAND "POINT" "11.511233,14.910015,-0.039820")
(COMMAND "POINT" "11.569641,14.887031,0.000000")
(COMMAND "POINT" "2.111431,16.592475,3.121973")
(COMMAND "POINT" "2.023148,16.812802,3.243793")
(COMMAND "POINT" "1.940857,17.025857,3.360134")
(COMMAND "POINT" "1.864557,17.231639,3.470994")
(COMMAND "POINT" "1.794249,17.430149,3.576373")
(COMMAND "POINT" "1.729934,17.621386,3.676273")
(COMMAND "POINT" "1.671609,17.805350,3.770692")
(COMMAND "POINT" "1.619277,17.982041,3.859632")
(COMMAND "POINT" "1.572936,18.151460,3.943091")
(COMMAND "POINT" "1.532587,18.313606,4.021069")
(COMMAND "POINT" "1.498230,18.468479,4.093568")
(COMMAND "POINT" "1.469865,18.616080,4.160586")
(COMMAND "POINT" "1.447491,18.756407,4.222124")
(COMMAND "POINT" "1.431109,18.889463,4.278182")
(COMMAND "POINT" "1.420719,19.015245,4.328760")
(COMMAND "POINT" "1.416321,19.133755,4.373857")
(COMMAND "POINT" "1.417914,19.244992,4.413474")
(COMMAND "POINT" "1.425499,19.348957,4.447611")
(COMMAND "POINT" "1.439076,19.445648,4.476268")
(COMMAND "POINT" "1.458644,19.535067,4.499444")
(COMMAND "POINT" "1.484205,19.617214,4.517140")
(COMMAND "POINT" "1.515757,19.692087,4.529356")
(COMMAND "POINT" "1.553301,19.759688,4.536092")
(COMMAND "POINT" "1.596836,19.820017,4.537348")
(COMMAND "POINT" "1.646364,19.873072,4.533123")
(COMMAND "POINT" "1.701883,19.918855,4.523418")
(COMMAND "POINT" "1.763393,19.957365,4.508233")
(COMMAND "POINT" "1.830896,19.988603,4.487568")
(COMMAND "POINT" "1.904390,20.012567,4.461423")
(COMMAND "POINT" "1.983876,20.029259,4.429797")
(COMMAND "POINT" "2.069354,20.038679,4.392691")
(COMMAND "POINT" "2.160824,20.040826,4.350105")
(COMMAND "POINT" "2.258285,20.035700,4.302038")
(COMMAND "POINT" "2.361738,20.023301,4.248492")
(COMMAND "POINT" "2.471183,20.003629,4.189465")
(COMMAND "POINT" "2.586620,19.976685,4.124958")
(COMMAND "POINT" "2.708048,19.942469,4.054970")
(COMMAND "POINT" "2.835468,19.900979,3.979503")
(COMMAND "POINT" "2.968880,19.852217,3.898555")
(COMMAND "POINT" "3.108284,19.796182,3.812127")
(COMMAND "POINT" "3.253679,19.732874,3.720219")
(COMMAND "POINT" "3.405066,19.662294,3.622830")
(COMMAND "POINT" "3.562445,19.584441,3.519962")
(COMMAND "POINT" "3.725816,19.499316,3.411613")
(COMMAND "POINT" "3.895178,19.406917,3.297784")
(COMMAND "POINT" "4.070532,19.307246,3.178474")
(COMMAND "POINT" "4.251878,19.200302,3.053685")
(COMMAND "POINT" "4.439216,19.086086,2.923415")
(COMMAND "POINT" "4.632545,18.964597,2.787665")
(COMMAND "POINT" "4.831866,18.835835,2.646435")
(COMMAND "POINT" "5.036046,18.700985,2.500888")
(COMMAND "POINT" "5.238286,18.567154,2.358004")
(COMMAND "POINT" "5.437453,18.435527,2.218948")
(COMMAND "POINT" "5.633548,18.306104,2.083718")
(COMMAND "POINT" "5.826570,18.178884,1.952315")
(COMMAND "POINT" "6.016519,18.053868,1.824739")
(COMMAND "POINT" "6.203395,17.931056,1.700990")
(COMMAND "POINT" "6.387199,17.810447,1.581067")
(COMMAND "POINT" "6.567930,17.692042,1.464972")
(COMMAND "POINT" "6.745588,17.575841,1.352703")
(COMMAND "POINT" "6.920174,17.461843,1.244262")
(COMMAND "POINT" "7.091686,17.350049,1.139647")
(COMMAND "POINT" "7.260126,17.240459,1.038859")
(COMMAND "POINT" "7.425493,17.133072,0.941898")
(COMMAND "POINT" "7.587788,17.027890,0.848764")
(COMMAND "POINT" "7.747009,16.924911,0.759456")
(COMMAND "POINT" "7.903158,16.824135,0.673976")
(COMMAND "POINT" "8.056235,16.725563,0.592322")
(COMMAND "POINT" "8.206238,16.629195,0.514496")
(COMMAND "POINT" "8.353169,16.535031,0.440496")
(COMMAND "POINT" "8.497027,16.443070,0.370323")
(COMMAND "POINT" "8.637812,16.353313,0.303977")
(COMMAND "POINT" "8.775525,16.265760,0.241458")
(COMMAND "POINT" "8.910164,16.180411,0.182766")
(COMMAND "POINT" "9.041731,16.097265,0.127900")
(COMMAND "POINT" "9.170226,16.016323,0.076862")
(COMMAND "POINT" "9.295647,15.937584,0.029650")
(COMMAND "POINT" "9.417996,15.861049,-0.013735")
(COMMAND "POINT" "9.537272,15.786718,-0.053293")
(COMMAND "POINT" "9.653475,15.714591,-0.089024")
(COMMAND "POINT" "9.766606,15.644667,-0.120928")
(COMMAND "POINT" "9.876663,15.576947,-0.149005")
(COMMAND "POINT" "9.983648,15.511431,-0.173255")
(COMMAND "POINT" "10.087561,15.448118,-0.193679")
(COMMAND "POINT" "10.188400,15.387009,-0.210276")
(COMMAND "POINT" "10.286167,15.328104,-0.223045")
(COMMAND "POINT" "10.380861,15.271403,-0.231988")
(COMMAND "POINT" "10.472482,15.216905,-0.237104")
(COMMAND "POINT" "10.561031,15.164611,-0.238393")
(COMMAND "POINT" "10.646507,15.114520,-0.235856")
(COMMAND "POINT" "10.728910,15.066634,-0.229491")
(COMMAND "POINT" "10.808240,15.020950,-0.219300")
(COMMAND "POINT" "10.884498,14.977471,-0.205281")
(COMMAND "POINT" "10.957683,14.936195,-0.187436")
(COMMAND "POINT" "11.027795,14.897123,-0.165764")
(COMMAND "POINT" "11.094834,14.860255,-0.140265")
(COMMAND "POINT" "11.158801,14.825591,-0.110939")
(COMMAND "POINT" "11.219695,14.793130,-0.077786")
(COMMAND "POINT" "11.277516,14.762872,-0.040807")
(COMMAND "POINT" "11.332264,14.734819,0.000000")
(COMMAND "POINT" "2.079588,16.650316,3.198203")
(COMMAND "POINT" "1.983530,16.877971,3.322998")
(COMMAND "POINT" "1.893654,17.098091,3.442179")
(COMMAND "POINT" "1.809959,17.310675,3.555746")
(COMMAND "POINT" "1.732447,17.515724,3.663699")
(COMMAND "POINT" "1.661116,17.713237,3.766038")
(COMMAND "POINT" "1.595968,17.903215,3.862762")
(COMMAND "POINT" "1.537001,18.085658,3.953873")
(COMMAND "POINT" "1.484216,18.260566,4.039370")
(COMMAND "POINT" "1.437613,18.427939,4.119253")
(COMMAND "POINT" "1.397191,18.587776,4.193522")
(COMMAND "POINT" "1.362952,18.740078,4.262176")
(COMMAND "POINT" "1.334895,18.884844,4.325217")
(COMMAND "POINT" "1.313019,19.022076,4.382643")
(COMMAND "POINT" "1.297325,19.151772,4.434456")
(COMMAND "POINT" "1.287813,19.273932,4.480655")
(COMMAND "POINT" "1.284483,19.388558,4.521239")
(COMMAND "POINT" "1.287335,19.495648,4.556210")
(COMMAND "POINT" "1.296368,19.595203,4.585566")
(COMMAND "POINT" "1.311584,19.687223,4.609308")
(COMMAND "POINT" "1.332981,19.771707,4.627437")
(COMMAND "POINT" "1.360560,19.848656,4.639951")
(COMMAND "POINT" "1.394321,19.918070,4.646851")
(COMMAND "POINT" "1.434264,19.979948,4.648138")
(COMMAND "POINT" "1.480389,20.034292,4.643810")
(COMMAND "POINT" "1.532696,20.081100,4.633868")
(COMMAND "POINT" "1.591184,20.120372,4.618312")
(COMMAND "POINT" "1.655855,20.152110,4.597142")
(COMMAND "POINT" "1.726707,20.176312,4.570358")
(COMMAND "POINT" "1.803741,20.192978,4.537960")
(COMMAND "POINT" "1.886957,20.202110,4.499948")
(COMMAND "POINT" "1.976355,20.203706,4.456322")
(COMMAND "POINT" "2.071934,20.197767,4.407082")
(COMMAND "POINT" "2.173696,20.184293,4.352228")
(COMMAND "POINT" "2.281639,20.163283,4.291760")
(COMMAND "POINT" "2.395764,20.134738,4.225678")
(COMMAND "POINT" "2.516071,20.098658,4.153982")
(COMMAND "POINT" "2.642560,20.055043,4.076671")
(COMMAND "POINT" "2.775231,20.003892,3.993747")
(COMMAND "POINT" "2.914084,19.945206,3.905209")
(COMMAND "POINT" "3.059118,19.878985,3.811056")
(COMMAND "POINT" "3.210335,19.805228,3.711290")
(COMMAND "POINT" "3.367733,19.723936,3.605910")
(COMMAND "POINT" "3.531313,19.635109,3.494915")
(COMMAND "POINT" "3.701075,19.538747,3.378307")
(COMMAND "POINT" "3.877019,19.434849,3.256084")
(COMMAND "POINT" "4.059145,19.323416,3.128248")
(COMMAND "POINT" "4.247452,19.204448,2.994797")
(COMMAND "POINT" "4.441941,19.077944,2.855732")
(COMMAND "POINT" "4.642613,18.943905,2.711054")
(COMMAND "POINT" "4.848295,18.803550,2.561953")
(COMMAND "POINT" "5.051966,18.664187,2.415580")
(COMMAND "POINT" "5.252454,18.527035,2.273128")
(COMMAND "POINT" "5.449759,18.392094,2.134596")
(COMMAND "POINT" "5.643883,18.259364,1.999985")
(COMMAND "POINT" "5.834823,18.128845,1.869294")
(COMMAND "POINT" "6.022581,18.000538,1.742523")
(COMMAND "POINT" "6.207156,17.874441,1.619673")
(COMMAND "POINT" "6.388549,17.750555,1.500742")
(COMMAND "POINT" "6.566760,17.628881,1.385733")
(COMMAND "POINT" "6.741788,17.509418,1.274643")
(COMMAND "POINT" "6.913633,17.392165,1.167474")
(COMMAND "POINT" "7.082296,17.277124,1.064225")
(COMMAND "POINT" "7.247776,17.164294,0.964896")
(COMMAND "POINT" "7.410074,17.053675,0.869488")
(COMMAND "POINT" "7.569189,16.945267,0.778000")
(COMMAND "POINT" "7.725122,16.839070,0.690433")
(COMMAND "POINT" "7.877872,16.735084,0.606785")
(COMMAND "POINT" "8.027439,16.633309,0.527058")
(COMMAND "POINT" "8.173825,16.533746,0.451252")
(COMMAND "POINT" "8.317027,16.436393,0.379365")
(COMMAND "POINT" "8.457047,16.341251,0.311399")
(COMMAND "POINT" "8.593885,16.248321,0.247354")
(COMMAND "POINT" "8.727540,16.157601,0.187228")
(COMMAND "POINT" "8.858012,16.069093,0.131023")
(COMMAND "POINT" "8.985302,15.982796,0.078738")
(COMMAND "POINT" "9.109410,15.898710,0.030374")
(COMMAND "POINT" "9.230335,15.816835,-0.014070")
(COMMAND "POINT" "9.348077,15.737170,-0.054594")
(COMMAND "POINT" "9.462637,15.659717,-0.091197")
(COMMAND "POINT" "9.574014,15.584476,-0.123881")
(COMMAND "POINT" "9.682209,15.511445,-0.152643")
(COMMAND "POINT" "9.787222,15.440625,-0.177486")
(COMMAND "POINT" "9.889051,15.372016,-0.198408")
(COMMAND "POINT" "9.987699,15.305619,-0.215410")
(COMMAND "POINT" "10.083163,15.241432,-0.228492")
(COMMAND "POINT" "10.175445,15.179457,-0.237653")
(COMMAND "POINT" "10.264545,15.119692,-0.242894")
(COMMAND "POINT" "10.350462,15.062139,-0.244214")
(COMMAND "POINT" "10.433197,15.006797,-0.241615")
(COMMAND "POINT" "10.512749,14.953666,-0.235095")
(COMMAND "POINT" "10.589119,14.902745,-0.224654")
(COMMAND "POINT" "10.662306,14.854036,-0.210294")
(COMMAND "POINT" "10.732310,14.807539,-0.192013")
(COMMAND "POINT" "10.799132,14.763252,-0.169811")
(COMMAND "POINT" "10.862772,14.721176,-0.143690")
(COMMAND "POINT" "10.923229,14.681311,-0.113648")
(COMMAND "POINT" "10.980503,14.643657,-0.079685")
(COMMAND "POINT" "11.034595,14.608215,-0.041803")
(COMMAND "POINT" "11.085504,14.574983,0.000000")
(COMMAND "POINT" "2.049147,16.707459,3.275187")
(COMMAND "POINT" "1.945137,16.942430,3.402986")
(COMMAND "POINT" "1.847501,17.169603,3.525036")
(COMMAND "POINT" "1.756241,17.388976,3.641336")
(COMMAND "POINT" "1.671355,17.600550,3.751888")
(COMMAND "POINT" "1.592844,17.804324,3.856690")
(COMMAND "POINT" "1.520708,18.000299,3.955743")
(COMMAND "POINT" "1.454947,18.188475,4.049047")
(COMMAND "POINT" "1.395560,18.368852,4.136602")
(COMMAND "POINT" "1.342548,18.541429,4.218407")
(COMMAND "POINT" "1.295911,18.706207,4.294464")
(COMMAND "POINT" "1.255649,18.863186,4.364771")
(COMMAND "POINT" "1.221762,19.012365,4.429329")
(COMMAND "POINT" "1.194249,19.153745,4.488138")
(COMMAND "POINT" "1.173112,19.287326,4.541198")
(COMMAND "POINT" "1.158349,19.413107,4.588508")
(COMMAND "POINT" "1.149961,19.531089,4.630070")
(COMMAND "POINT" "1.147947,19.641272,4.665882")
(COMMAND "POINT" "1.152309,19.743655,4.695945")
(COMMAND "POINT" "1.163045,19.838239,4.720259")
(COMMAND "POINT" "1.180156,19.925024,4.738824")
(COMMAND "POINT" "1.203642,20.004009,4.751639")
(COMMAND "POINT" "1.233503,20.075195,4.758706")
(COMMAND "POINT" "1.269739,20.138582,4.760023")
(COMMAND "POINT" "1.312349,20.194169,4.755591")
(COMMAND "POINT" "1.361334,20.241958,4.745410")
(COMMAND "POINT" "1.416694,20.281946,4.729480")
(COMMAND "POINT" "1.478429,20.314136,4.707800")
(COMMAND "POINT" "1.546538,20.338526,4.680371")
(COMMAND "POINT" "1.621023,20.355117,4.647194")
(COMMAND "POINT" "1.701882,20.363909,4.608267")
(COMMAND "POINT" "1.789116,20.364901,4.563590")
(COMMAND "POINT" "1.882725,20.358094,4.513165")
(COMMAND "POINT" "1.982708,20.343487,4.456991")
(COMMAND "POINT" "2.089066,20.321082,4.395067")
(COMMAND "POINT" "2.201800,20.290877,4.327394")
(COMMAND "POINT" "2.320908,20.252872,4.253972")
(COMMAND "POINT" "2.446390,20.207069,4.174801")
(COMMAND "POINT" "2.578248,20.153466,4.089881")
(COMMAND "POINT" "2.716480,20.092063,3.999211")
(COMMAND "POINT" "2.861088,20.022862,3.902792")
(COMMAND "POINT" "3.012070,19.945861,3.800624")
(COMMAND "POINT" "3.169426,19.861061,3.692707")
(COMMAND "POINT" "3.333158,19.768461,3.579041")
(COMMAND "POINT" "3.503264,19.668062,3.459626")
(COMMAND "POINT" "3.679746,19.559864,3.334461")
(COMMAND "POINT" "3.862602,19.443866,3.203548")
(COMMAND "POINT" "4.051832,19.320069,3.066885")
(COMMAND "POINT" "4.247438,19.188473,2.924473")
(COMMAND "POINT" "4.449418,19.049078,2.776311")
(COMMAND "POINT" "4.656565,18.903135,2.623621")
(COMMAND "POINT" "4.861625,18.758158,2.473726")
(COMMAND "POINT" "5.063390,18.615399,2.327845")
(COMMAND "POINT" "5.261860,18.474858,2.185978")
(COMMAND "POINT" "5.457034,18.336535,2.048127")
(COMMAND "POINT" "5.648913,18.200430,1.914290")
(COMMAND "POINT" "5.837497,18.066542,1.784467")
(COMMAND "POINT" "6.022786,17.934873,1.658660")
(COMMAND "POINT" "6.204780,17.805421,1.536867")
(COMMAND "POINT" "6.383478,17.678188,1.419089")
(COMMAND "POINT" "6.558882,17.553172,1.305325")
(COMMAND "POINT" "6.730990,17.430374,1.195576")
(COMMAND "POINT" "6.899803,17.309794,1.089842")
(COMMAND "POINT" "7.065321,17.191432,0.988122")
(COMMAND "POINT" "7.227543,17.075288,0.890418")
(COMMAND "POINT" "7.386470,16.961362,0.796727")
(COMMAND "POINT" "7.542103,16.849654,0.707052")
(COMMAND "POINT" "7.694440,16.740163,0.621391")
(COMMAND "POINT" "7.843481,16.632891,0.539745")
(COMMAND "POINT" "7.989228,16.527836,0.462114")
(COMMAND "POINT" "8.131679,16.424999,0.388497")
(COMMAND "POINT" "8.270835,16.324381,0.318895")
(COMMAND "POINT" "8.406696,16.225980,0.253308")
(COMMAND "POINT" "8.539262,16.129797,0.191735")
(COMMAND "POINT" "8.668533,16.035832,0.134177")
(COMMAND "POINT" "8.794508,15.944085,0.080634")
(COMMAND "POINT" "8.917189,15.854555,0.031105")
(COMMAND "POINT" "9.036574,15.767244,-0.014409")
(COMMAND "POINT" "9.152663,15.682150,-0.055908")
(COMMAND "POINT" "9.265458,15.599275,-0.093393")
(COMMAND "POINT" "9.374958,15.518617,-0.126862")
(COMMAND "POINT" "9.481162,15.440178,-0.156318")
(COMMAND "POINT" "9.584071,15.363956,-0.181758")
(COMMAND "POINT" "9.683685,15.289952,-0.203184")
(COMMAND "POINT" "9.780003,15.218166,-0.220595")
(COMMAND "POINT" "9.873027,15.148598,-0.233992")
(COMMAND "POINT" "9.962755,15.081248,-0.243373")
(COMMAND "POINT" "10.049188,15.016115,-0.248740")
(COMMAND "POINT" "10.132326,14.953201,-0.250093")
(COMMAND "POINT" "10.212169,14.892504,-0.247431")
(COMMAND "POINT" "10.288717,14.834026,-0.240754")
(COMMAND "POINT" "10.361969,14.777765,-0.230062")
(COMMAND "POINT" "10.431926,14.723722,-0.215356")
(COMMAND "POINT" "10.498588,14.671898,-0.196635")
(COMMAND "POINT" "10.561955,14.622291,-0.173899")
(COMMAND "POINT" "10.622026,14.574902,-0.147148")
(COMMAND "POINT" "10.678803,14.529730,-0.116383")
(COMMAND "POINT" "10.732284,14.486777,-0.081604")
(COMMAND "POINT" "10.782470,14.446042,-0.042809")
(COMMAND "POINT" "10.829361,14.407524,0.000000")
(COMMAND "POINT" "2.020108,16.763901,3.352924")
(COMMAND "POINT" "1.907968,17.006180,3.483757")
(COMMAND "POINT" "1.802400,17.240394,3.608704")
(COMMAND "POINT" "1.703401,17.466543,3.727765")
(COMMAND "POINT" "1.610974,17.684627,3.840940")
(COMMAND "POINT" "1.525116,17.894647,3.948230")
(COMMAND "POINT" "1.445830,18.096602,4.049634")
(COMMAND "POINT" "1.373114,18.290492,4.145153")
(COMMAND "POINT" "1.306969,18.476317,4.234786")
(COMMAND "POINT" "1.247394,18.654077,4.318533")
(COMMAND "POINT" "1.194390,18.823773,4.396394")
(COMMAND "POINT" "1.147956,18.985403,4.468370")
(COMMAND "POINT" "1.108093,19.138969,4.534461")
(COMMAND "POINT" "1.074801,19.284470,4.594666")
(COMMAND "POINT" "1.048079,19.421907,4.648985")
(COMMAND "POINT" "1.027928,19.551278,4.697418")
(COMMAND "POINT" "1.014347,19.672585,4.739966")
(COMMAND "POINT" "1.007337,19.785827,4.776628")
(COMMAND "POINT" "1.006897,19.891004,4.807405")
(COMMAND "POINT" "1.013029,19.988116,4.832296")
(COMMAND "POINT" "1.025730,20.077164,4.851301")
(COMMAND "POINT" "1.045002,20.158147,4.864421")
(COMMAND "POINT" "1.070845,20.231064,4.871655")
(COMMAND "POINT" "1.103259,20.295918,4.873004")
(COMMAND "POINT" "1.142243,20.352706,4.868467")
(COMMAND "POINT" "1.187797,20.401429,4.858044")
(COMMAND "POINT" "1.239923,20.442088,4.841735")
(COMMAND "POINT" "1.298618,20.474682,4.819541")
(COMMAND "POINT" "1.363885,20.499211,4.791462")
(COMMAND "POINT" "1.435722,20.515675,4.757496")
(COMMAND "POINT" "1.514129,20.524075,4.717645")
(COMMAND "POINT" "1.599107,20.524409,4.671909")
(COMMAND "POINT" "1.690656,20.516679,4.620287")
(COMMAND "POINT" "1.788775,20.500884,4.562779")
(COMMAND "POINT" "1.893465,20.477025,4.499385")
(COMMAND "POINT" "2.004726,20.445100,4.430106")
(COMMAND "POINT" "2.122557,20.405111,4.354942")
(COMMAND "POINT" "2.246958,20.357056,4.273891")
(COMMAND "POINT" "2.377930,20.300938,4.186955")
(COMMAND "POINT" "2.515473,20.236754,4.094134")
(COMMAND "POINT" "2.659587,20.164505,3.995427")
(COMMAND "POINT" "2.810271,20.084192,3.890834")
(COMMAND "POINT" "2.967525,19.995814,3.780355")
(COMMAND "POINT" "3.131350,19.899371,3.663991")
(COMMAND "POINT" "3.301746,19.794863,3.541741")
(COMMAND "POINT" "3.478712,19.682290,3.413606")
(COMMAND "POINT" "3.662249,19.561653,3.279585")
(COMMAND "POINT" "3.852357,19.432951,3.139678")
(COMMAND "POINT" "4.049035,19.296184,2.993886")
(COMMAND "POINT" "4.252283,19.151352,2.842208")
(COMMAND "POINT" "4.460855,18.999742,2.685894")
(COMMAND "POINT" "4.667263,18.849069,2.532440")
(COMMAND "POINT" "4.870261,18.700621,2.383097")
(COMMAND "POINT" "5.069848,18.554397,2.237863")
(COMMAND "POINT" "5.266024,18.410397,2.096740")
(COMMAND "POINT" "5.458790,18.268621,1.959726")
(COMMAND "POINT" "5.648145,18.129070,1.826822")
(COMMAND "POINT" "5.834089,17.991743,1.698029")
(COMMAND "POINT" "6.016622,17.856640,1.573345")
(COMMAND "POINT" "6.195744,17.723761,1.452771")
(COMMAND "POINT" "6.371456,17.593106,1.336307")
(COMMAND "POINT" "6.543757,17.464676,1.223954")
(COMMAND "POINT" "6.712647,17.338469,1.115710")
(COMMAND "POINT" "6.878127,17.214487,1.011576")
(COMMAND "POINT" "7.040196,17.092729,0.911552")
(COMMAND "POINT" "7.198854,16.973196,0.815638")
(COMMAND "POINT" "7.354101,16.855886,0.723834")
(COMMAND "POINT" "7.505938,16.740801,0.636140")
(COMMAND "POINT" "7.654363,16.627939,0.552556")
(COMMAND "POINT" "7.799379,16.517302,0.473082")
(COMMAND "POINT" "7.940983,16.408890,0.397718")
(COMMAND "POINT" "8.079176,16.302701,0.326464")
(COMMAND "POINT" "8.213959,16.198737,0.259320")
(COMMAND "POINT" "8.345331,16.096997,0.196286")
(COMMAND "POINT" "8.473293,15.997481,0.137362")
(COMMAND "POINT" "8.597843,15.900189,0.082548")
(COMMAND "POINT" "8.718983,15.805121,0.031843")
(COMMAND "POINT" "8.836712,15.712278,-0.014751")
(COMMAND "POINT" "8.951031,15.621658,-0.057235")
(COMMAND "POINT" "9.061938,15.533263,-0.095609")
(COMMAND "POINT" "9.169435,15.447092,-0.129874")
(COMMAND "POINT" "9.273521,15.363146,-0.160028")
(COMMAND "POINT" "9.374196,15.281423,-0.186072")
(COMMAND "POINT" "9.471461,15.201925,-0.208007")
(COMMAND "POINT" "9.565315,15.124651,-0.225831")
(COMMAND "POINT" "9.655758,15.049601,-0.239545")
(COMMAND "POINT" "9.742791,14.976775,-0.249150")
(COMMAND "POINT" "9.826412,14.906174,-0.254644")
(COMMAND "POINT" "9.906623,14.837796,-0.256029")
(COMMAND "POINT" "9.983423,14.771643,-0.253303")
(COMMAND "POINT" "10.056813,14.707714,-0.246468")
(COMMAND "POINT" "10.126791,14.646009,-0.235523")
(COMMAND "POINT" "10.193359,14.586529,-0.220467")
(COMMAND "POINT" "10.256516,14.529272,-0.201302")
(COMMAND "POINT" "10.316263,14.474240,-0.178026")
(COMMAND "POINT" "10.372598,14.421432,-0.150641")
(COMMAND "POINT" "10.425523,14.370848,-0.119146")
(COMMAND "POINT" "10.475038,14.322489,-0.083540")
(COMMAND "POINT" "10.521141,14.276353,-0.043825")
(COMMAND "POINT" "10.563834,14.232442,0.000000")
(COMMAND "POINT" "1.992471,16.819644,3.431416")
(COMMAND "POINT" "1.872025,17.069220,3.565311")
(COMMAND "POINT" "1.758349,17.310464,3.693183")
(COMMAND "POINT" "1.651441,17.543376,3.815031")
(COMMAND "POINT" "1.551303,17.767956,3.930856")
(COMMAND "POINT" "1.457934,17.984205,4.040657")
(COMMAND "POINT" "1.371334,18.192122,4.144436")
(COMMAND "POINT" "1.291503,18.391707,4.242190")
(COMMAND "POINT" "1.218442,18.582961,4.333921")
(COMMAND "POINT" "1.152150,18.765883,4.419629")
(COMMAND "POINT" "1.092627,18.940473,4.499314")
(COMMAND "POINT" "1.039873,19.106731,4.572975")
(COMMAND "POINT" "0.993888,19.264657,4.640612")
(COMMAND "POINT" "0.954673,19.414252,4.702226")
(COMMAND "POINT" "0.922227,19.555515,4.757817")
(COMMAND "POINT" "0.896550,19.688447,4.807384")
(COMMAND "POINT" "0.877642,19.813046,4.850928")
(COMMAND "POINT" "0.865503,19.929314,4.888449")
(COMMAND "POINT" "0.860134,20.037250,4.919946")
(COMMAND "POINT" "0.861534,20.136855,4.945420")
(COMMAND "POINT" "0.869703,20.228127,4.964870")
(COMMAND "POINT" "0.884641,20.311068,4.978297")
(COMMAND "POINT" "0.906348,20.385677,4.985700")
(COMMAND "POINT" "0.934825,20.451955,4.987080")
(COMMAND "POINT" "0.970071,20.509901,4.982437")
(COMMAND "POINT" "1.012086,20.559514,4.971770")
(COMMAND "POINT" "1.060870,20.600797,4.955080")
(COMMAND "POINT" "1.116423,20.633747,4.932366")
(COMMAND "POINT" "1.178746,20.658366,4.903629")
(COMMAND "POINT" "1.247838,20.674653,4.868869")
(COMMAND "POINT" "1.323699,20.682608,4.828085")
(COMMAND "POINT" "1.406329,20.682232,4.781278")
(COMMAND "POINT" "1.495729,20.673524,4.728447")
(COMMAND "POINT" "1.591897,20.656484,4.669593")
(COMMAND "POINT" "1.694835,20.631112,4.604716")
(COMMAND "POINT" "1.804542,20.597409,4.533815")
(COMMAND "POINT" "1.921018,20.555373,4.456890")
(COMMAND "POINT" "2.044264,20.505006,4.373943")
(COMMAND "POINT" "2.174279,20.446308,4.284971")
(COMMAND "POINT" "2.311062,20.379277,4.189977")
(COMMAND "POINT" "2.454615,20.303915,4.088959")
(COMMAND "POINT" "2.604938,20.220221,3.981918")
(COMMAND "POINT" "2.762029,20.128196,3.868853")
(COMMAND "POINT" "2.925890,20.027839,3.749765")
(COMMAND "POINT" "3.096520,19.919149,3.624653")
(COMMAND "POINT" "3.273919,19.802129,3.493518")
(COMMAND "POINT" "3.458087,19.676776,3.356360")
(COMMAND "POINT" "3.649025,19.543092,3.213178")
(COMMAND "POINT" "3.846731,19.401076,3.063973")
(COMMAND "POINT" "4.051207,19.250728,2.908744")
(COMMAND "POINT" "4.261165,19.093369,2.748771")
(COMMAND "POINT" "4.468881,18.936919,2.591725")
(COMMAND "POINT" "4.673068,18.782700,2.438885")
(COMMAND "POINT" "4.873725,18.630710,2.290251")
(COMMAND "POINT" "5.070853,18.480950,2.145824")
(COMMAND "POINT" "5.264453,18.333420,2.005603")
(COMMAND "POINT" "5.454523,18.188120,1.869588")
(COMMAND "POINT" "5.641063,18.045050,1.737779")
(COMMAND "POINT" "5.824075,17.904210,1.610177")
(COMMAND "POINT" "6.003557,17.765600,1.486780")
(COMMAND "POINT" "6.179511,17.629220,1.367590")
(COMMAND "POINT" "6.351935,17.495070,1.252606")
(COMMAND "POINT" "6.520830,17.363149,1.141828")
(COMMAND "POINT" "6.686195,17.233459,1.035257")
(COMMAND "POINT" "6.848032,17.105998,0.932891")
(COMMAND "POINT" "7.006339,16.980768,0.834732")
(COMMAND "POINT" "7.161117,16.857767,0.740779")
(COMMAND "POINT" "7.312366,16.736997,0.651032")
(COMMAND "POINT" "7.460086,16.618456,0.565491")
(COMMAND "POINT" "7.604277,16.502145,0.484157")
(COMMAND "POINT" "7.744938,16.388064,0.407029")
(COMMAND "POINT" "7.882070,16.276213,0.334107")
(COMMAND "POINT" "8.015673,16.166592,0.265391")
(COMMAND "POINT" "8.145747,16.059201,0.200881")
(COMMAND "POINT" "8.272292,15.954040,0.140577")
(COMMAND "POINT" "8.395307,15.851108,0.084480")
(COMMAND "POINT" "8.514794,15.750407,0.032589")
(COMMAND "POINT" "8.630751,15.651936,-0.015096")
(COMMAND "POINT" "8.743179,15.555694,-0.058575")
(COMMAND "POINT" "8.852077,15.461683,-0.097848")
(COMMAND "POINT" "8.957447,15.369901,-0.132914")
(COMMAND "POINT" "9.059287,15.280349,-0.163774")
(COMMAND "POINT" "9.157598,15.193027,-0.190428")
(COMMAND "POINT" "9.252380,15.107936,-0.212876")
(COMMAND "POINT" "9.343633,15.025074,-0.231118")
(COMMAND "POINT" "9.431357,14.944442,-0.245153")
(COMMAND "POINT" "9.515551,14.866040,-0.254982")
(COMMAND "POINT" "9.596217,14.789868,-0.260606")
(COMMAND "POINT" "9.673353,14.715925,-0.262022")
(COMMAND "POINT" "9.746959,14.644213,-0.259233")
(COMMAND "POINT" "9.817037,14.574731,-0.252238")
(COMMAND "POINT" "9.883586,14.507478,-0.241036")
(COMMAND "POINT" "9.946605,14.442456,-0.225628")
(COMMAND "POINT" "10.006095,14.379663,-0.206014")
(COMMAND "POINT" "10.062056,14.319101,-0.182194")
(COMMAND "POINT" "10.114488,14.260768,-0.154168")
(COMMAND "POINT" "10.163391,14.204665,-0.121935")
(COMMAND "POINT" "10.208764,14.150792,-0.085496")
(COMMAND "POINT" "10.250608,14.099149,-0.044851")
(COMMAND "POINT" "10.288923,14.049736,0.000000")
(COMMAND "POINT" "1.966236,16.874687,3.510661")
(COMMAND "POINT" "1.837307,17.131550,3.647649")
(COMMAND "POINT" "1.715348,17.379812,3.778474")
(COMMAND "POINT" "1.600360,17.619474,3.903136")
(COMMAND "POINT" "1.492343,17.850537,4.021636")
(COMMAND "POINT" "1.391296,18.072999,4.133973")
(COMMAND "POINT" "1.297220,18.286860,4.240147")
(COMMAND "POINT" "1.210115,18.492122,4.340160")
(COMMAND "POINT" "1.129980,18.688784,4.434009")
(COMMAND "POINT" "1.056816,18.876845,4.521696")
(COMMAND "POINT" "0.990622,19.056307,4.603221")
(COMMAND "POINT" "0.931399,19.227168,4.678583")
(COMMAND "POINT" "0.879147,19.389429,4.747783")
(COMMAND "POINT" "0.833866,19.543090,4.810820")
(COMMAND "POINT" "0.795555,19.688151,4.867694")
(COMMAND "POINT" "0.764215,19.824612,4.918407")
(COMMAND "POINT" "0.739845,19.952473,4.962956")
(COMMAND "POINT" "0.722446,20.071733,5.001343")
(COMMAND "POINT" "0.712018,20.182394,5.033568")
(COMMAND "POINT" "0.708561,20.284454,5.059630")
(COMMAND "POINT" "0.712074,20.377914,5.079529")
(COMMAND "POINT" "0.722558,20.462774,5.093266")
(COMMAND "POINT" "0.740012,20.539034,5.100840")
(COMMAND "POINT" "0.764437,20.606694,5.102252")
(COMMAND "POINT" "0.795833,20.665754,5.097502")
(COMMAND "POINT" "0.834199,20.716213,5.086589")
(COMMAND "POINT" "0.879536,20.758073,5.069513")
(COMMAND "POINT" "0.931844,20.791332,5.046275")
(COMMAND "POINT" "0.991122,20.815991,5.016874")
(COMMAND "POINT" "1.057371,20.832050,4.981311")
(COMMAND "POINT" "1.130591,20.839509,4.939585")
(COMMAND "POINT" "1.210781,20.838368,4.891697")
(COMMAND "POINT" "1.297942,20.828627,4.837646")
(COMMAND "POINT" "1.392074,20.810285,4.777433")
(COMMAND "POINT" "1.493176,20.783344,4.711057")
(COMMAND "POINT" "1.601249,20.747802,4.638519")
(COMMAND "POINT" "1.716293,20.703660,4.559818")
(COMMAND "POINT" "1.838307,20.650918,4.474955")
(COMMAND "POINT" "1.967292,20.589576,4.383929")
(COMMAND "POINT" "2.103248,20.519634,4.286741")
(COMMAND "POINT" "2.246174,20.441092,4.183390")
(COMMAND "POINT" "2.396071,20.353950,4.073876")
(COMMAND "POINT" "2.552939,20.258207,3.958200")
(COMMAND "POINT" "2.716777,20.153864,3.836362")
(COMMAND "POINT" "2.887586,20.040922,3.708361")
(COMMAND "POINT" "3.065365,19.919379,3.574198")
(COMMAND "POINT" "3.250115,19.789236,3.433872")
(COMMAND "POINT" "3.441836,19.650493,3.287383")
(COMMAND "POINT" "3.640528,19.503149,3.134732")
(COMMAND "POINT" "3.846190,19.347206,2.975919")
(COMMAND "POINT" "4.057495,19.184017,2.812251")
(COMMAND "POINT" "4.266478,19.021709,2.651578")
(COMMAND "POINT" "4.471809,18.861635,2.495209")
(COMMAND "POINT" "4.673491,18.703797,2.343143")
(COMMAND "POINT" "4.871521,18.548194,2.195380")
(COMMAND "POINT" "5.065902,18.394826,2.051921")
(COMMAND "POINT" "5.256631,18.243694,1.912764")
(COMMAND "POINT" "5.443711,18.094796,1.777912")
(COMMAND "POINT" "5.627140,17.948133,1.647362")
(COMMAND "POINT" "5.806918,17.803706,1.521116")
(COMMAND "POINT" "5.983045,17.661514,1.399173")
(COMMAND "POINT" "6.155523,17.521556,1.281534")
(COMMAND "POINT" "6.324349,17.383834,1.168198")
(COMMAND "POINT" "6.489526,17.248347,1.059165")
(COMMAND "POINT" "6.651051,17.115096,0.954436")
(COMMAND "POINT" "6.808926,16.984079,0.854009")
(COMMAND "POINT" "6.963151,16.855297,0.757887")
(COMMAND "POINT" "7.113725,16.728751,0.666067")
(COMMAND "POINT" "7.260649,16.604440,0.578551")
(COMMAND "POINT" "7.403922,16.482363,0.495338")
(COMMAND "POINT" "7.543545,16.362522,0.416429")
(COMMAND "POINT" "7.679517,16.244916,0.341822")
(COMMAND "POINT" "7.811838,16.129545,0.271520")
(COMMAND "POINT" "7.940510,16.016410,0.205520")
(COMMAND "POINT" "8.065530,15.905509,0.143824")
(COMMAND "POINT" "8.186900,15.796844,0.086431")
(COMMAND "POINT" "8.304620,15.690413,0.033341")
(COMMAND "POINT" "8.418689,15.586218,-0.015445")
(COMMAND "POINT" "8.529107,15.484258,-0.059928")
(COMMAND "POINT" "8.635875,15.384533,-0.100107")
(COMMAND "POINT" "8.738993,15.287043,-0.135983")
(COMMAND "POINT" "8.838460,15.191788,-0.167556")
(COMMAND "POINT" "8.934277,15.098768,-0.194826")
(COMMAND "POINT" "9.026443,15.007984,-0.217792")
(COMMAND "POINT" "9.114958,14.919434,-0.236455")
(COMMAND "POINT" "9.199823,14.833120,-0.250815")
(COMMAND "POINT" "9.281037,14.749041,-0.260871")
(COMMAND "POINT" "9.358601,14.667197,-0.266624")
(COMMAND "POINT" "9.432515,14.587588,-0.268074")
(COMMAND "POINT" "9.502778,14.510214,-0.265220")
(COMMAND "POINT" "9.569390,14.435075,-0.258063")
(COMMAND "POINT" "9.632352,14.362172,-0.246603")
(COMMAND "POINT" "9.691664,14.291503,-0.230839")
(COMMAND "POINT" "9.747324,14.223070,-0.210772")
(COMMAND "POINT" "9.799335,14.156872,-0.186402")
(COMMAND "POINT" "9.847695,14.092909,-0.157728")
(COMMAND "POINT" "9.892404,14.031181,-0.124751")
(COMMAND "POINT" "9.933463,13.971688,-0.087471")
(COMMAND "POINT" "9.970871,13.914430,-0.045887")
(COMMAND "POINT" "10.004629,13.859407,0.000000")
(COMMAND "POINT" "1.941404,16.929031,3.590661")
(COMMAND "POINT" "1.803814,17.193170,3.730770")
(COMMAND "POINT" "1.673399,17.448439,3.864576")
(COMMAND "POINT" "1.550158,17.694839,3.992079")
(COMMAND "POINT" "1.434093,17.932368,4.113279")
(COMMAND "POINT" "1.325203,18.161028,4.228176")
(COMMAND "POINT" "1.223488,18.380817,4.336770")
(COMMAND "POINT" "1.128948,18.591737,4.439061")
(COMMAND "POINT" "1.041582,18.793786,4.535049")
(COMMAND "POINT" "0.961392,18.986966,4.624735")
(COMMAND "POINT" "0.888376,19.171275,4.708117")
(COMMAND "POINT" "0.822536,19.346715,4.785196")
(COMMAND "POINT" "0.763870,19.513285,4.855973")
(COMMAND "POINT" "0.712379,19.670985,4.920447")
(COMMAND "POINT" "0.668064,19.819815,4.978617")
(COMMAND "POINT" "0.630923,19.959774,5.030485")
(COMMAND "POINT" "0.600957,20.090864,5.076049")
(COMMAND "POINT" "0.578166,20.213084,5.115311")
(COMMAND "POINT" "0.562551,20.326434,5.148270")
(COMMAND "POINT" "0.554110,20.430914,5.174926")
(COMMAND "POINT" "0.552844,20.526524,5.195279")
(COMMAND "POINT" "0.558753,20.613265,5.209329")
(COMMAND "POINT" "0.571836,20.691135,5.217076")
(COMMAND "POINT" "0.592095,20.760135,5.218520")
(COMMAND "POINT" "0.619529,20.820265,5.213661")
(COMMAND "POINT" "0.654138,20.871526,5.202499")
(COMMAND "POINT" "0.695921,20.913916,5.185035")
(COMMAND "POINT" "0.744880,20.947436,5.161267")
(COMMAND "POINT" "0.801014,20.972087,5.131196")
(COMMAND "POINT" "0.864322,20.987867,5.094823")
(COMMAND "POINT" "0.934806,20.994778,5.052146")
(COMMAND "POINT" "1.012464,20.992818,5.003167")
(COMMAND "POINT" "1.097298,20.981989,4.947884")
(COMMAND "POINT" "1.189306,20.962290,4.886299")
(COMMAND "POINT" "1.288489,20.933720,4.818411")
(COMMAND "POINT" "1.394847,20.896281,4.744219")
(COMMAND "POINT" "1.508380,20.849972,4.663725")
(COMMAND "POINT" "1.629089,20.794793,4.576928")
(COMMAND "POINT" "1.756972,20.730743,4.483828")
(COMMAND "POINT" "1.892030,20.657824,4.384425")
(COMMAND "POINT" "2.034263,20.576035,4.278719")
(COMMAND "POINT" "2.183671,20.485376,4.166710")
(COMMAND "POINT" "2.340253,20.385847,4.048398")
(COMMAND "POINT" "2.504011,20.277448,3.923783")
(COMMAND "POINT" "2.674944,20.160180,3.792865")
(COMMAND "POINT" "2.853052,20.034041,3.655645")
(COMMAND "POINT" "3.038334,19.899032,3.512121")
(COMMAND "POINT" "3.230792,19.755153,3.362294")
(COMMAND "POINT" "3.430424,19.602405,3.206165")
(COMMAND "POINT" "3.637232,19.440786,3.043732")
(COMMAND "POINT" "3.849846,19.271686,2.876335")
(COMMAND "POINT" "4.060053,19.103437,2.712001")
(COMMAND "POINT" "4.266486,18.937428,2.552068")
(COMMAND "POINT" "4.469145,18.773659,2.396537")
(COMMAND "POINT" "4.668028,18.612129,2.245407")
(COMMAND "POINT" "4.863137,18.452840,2.098679")
(COMMAND "POINT" "5.054471,18.295789,1.956352")
(COMMAND "POINT" "5.242031,18.140979,1.818426")
(COMMAND "POINT" "5.425815,17.988409,1.684902")
(COMMAND "POINT" "5.605825,17.838078,1.555779")
(COMMAND "POINT" "5.782060,17.689987,1.431057")
(COMMAND "POINT" "5.954521,17.544136,1.310737")
(COMMAND "POINT" "6.123207,17.400524,1.194818")
(COMMAND "POINT" "6.288118,17.259153,1.083301")
(COMMAND "POINT" "6.449254,17.120021,0.976185")
(COMMAND "POINT" "6.606616,16.983129,0.873470")
(COMMAND "POINT" "6.760203,16.848476,0.775157")
(COMMAND "POINT" "6.910015,16.716064,0.681245")
(COMMAND "POINT" "7.056052,16.585891,0.591735")
(COMMAND "POINT" "7.198315,16.457958,0.506626")
(COMMAND "POINT" "7.336803,16.332264,0.425918")
(COMMAND "POINT" "7.471516,16.208811,0.349612")
(COMMAND "POINT" "7.602455,16.087597,0.277707")
(COMMAND "POINT" "7.729619,15.968623,0.210203")
(COMMAND "POINT" "7.853008,15.851889,0.147101")
(COMMAND "POINT" "7.972622,15.737394,0.088401")
(COMMAND "POINT" "8.088462,15.625139,0.034101")
(COMMAND "POINT" "8.200527,15.515124,-0.015797")
(COMMAND "POINT" "8.308817,15.407349,-0.061293")
(COMMAND "POINT" "8.413333,15.301814,-0.102388")
(COMMAND "POINT" "8.514074,15.198518,-0.139082")
(COMMAND "POINT" "8.611040,15.097462,-0.171375")
(COMMAND "POINT" "8.704231,14.998646,-0.199266")
(COMMAND "POINT" "8.793648,14.902070,-0.222755")
(COMMAND "POINT" "8.879289,14.807733,-0.241843")
(COMMAND "POINT" "8.961157,14.715636,-0.256530")
(COMMAND "POINT" "9.039249,14.625779,-0.266816")
(COMMAND "POINT" "9.113567,14.538162,-0.272700")
(COMMAND "POINT" "9.184110,14.452784,-0.274182")
(COMMAND "POINT" "9.250878,14.369646,-0.271264")
(COMMAND "POINT" "9.313872,14.288748,-0.263944")
(COMMAND "POINT" "9.373091,14.210090,-0.252222")
(COMMAND "POINT" "9.428535,14.133671,-0.236099")
(COMMAND "POINT" "9.480204,14.059493,-0.215575")
(COMMAND "POINT" "9.528099,13.987554,-0.190649")
(COMMAND "POINT" "9.572219,13.917854,-0.161322")
(COMMAND "POINT" "9.612564,13.850395,-0.127594")
(COMMAND "POINT" "9.649135,13.785175,-0.089464")
(COMMAND "POINT" "9.681930,13.722195,-0.046933")
(COMMAND "POINT" "9.710952,13.661455,0.000000")
(COMMAND "POINT" "1.917973,16.982675,3.671414")
(COMMAND "POINT" "1.771545,17.254081,3.814674")
(COMMAND "POINT" "1.632500,17.516346,3.951489")
(COMMAND "POINT" "1.500836,17.769469,4.081859")
(COMMAND "POINT" "1.376554,18.013451,4.205785")
(COMMAND "POINT" "1.259655,18.248292,4.323266")
(COMMAND "POINT" "1.150138,18.473992,4.434303")
(COMMAND "POINT" "1.048002,18.690550,4.538894")
(COMMAND "POINT" "0.953249,18.897968,4.637042")
(COMMAND "POINT" "0.865878,19.096244,4.728744")
(COMMAND "POINT" "0.785889,19.285378,4.814001")
(COMMAND "POINT" "0.713282,19.465372,4.892814")
(COMMAND "POINT" "0.648057,19.636224,4.965183")
(COMMAND "POINT" "0.590214,19.797935,5.031106")
(COMMAND "POINT" "0.539753,19.950505,5.090585")
(COMMAND "POINT" "0.496674,20.093934,5.143619")
(COMMAND "POINT" "0.460978,20.228221,5.190209")
(COMMAND "POINT" "0.432663,20.353367,5.230353")
(COMMAND "POINT" "0.411731,20.469372,5.264053")
(COMMAND "POINT" "0.398180,20.576236,5.291309")
(COMMAND "POINT" "0.392012,20.673958,5.312119")
(COMMAND "POINT" "0.393226,20.762539,5.326485")
(COMMAND "POINT" "0.401822,20.841979,5.334407")
(COMMAND "POINT" "0.417799,20.912278,5.335883")
(COMMAND "POINT" "0.441159,20.973435,5.330915")
(COMMAND "POINT" "0.471901,21.025451,5.319502")
(COMMAND "POINT" "0.510026,21.068326,5.301645")
(COMMAND "POINT" "0.555532,21.102060,5.277342")
(COMMAND "POINT" "0.608420,21.126652,5.246596")
(COMMAND "POINT" "0.668690,21.142104,5.209404")
(COMMAND "POINT" "0.736343,21.148414,5.165768")
(COMMAND "POINT" "0.811377,21.145582,5.115687")
(COMMAND "POINT" "0.893794,21.133610,5.059161")
(COMMAND "POINT" "0.983592,21.112496,4.996191")
(COMMAND "POINT" "1.080773,21.082241,4.926775")
(COMMAND "POINT" "1.185336,21.042845,4.850916")
(COMMAND "POINT" "1.297281,20.994308,4.768611")
(COMMAND "POINT" "1.416608,20.936629,4.679862")
(COMMAND "POINT" "1.543317,20.869809,4.584668")
(COMMAND "POINT" "1.677408,20.793848,4.483029")
(COMMAND "POINT" "1.818881,20.708745,4.374946")
(COMMAND "POINT" "1.967736,20.614502,4.260418")
(COMMAND "POINT" "2.123974,20.511117,4.139446")
(COMMAND "POINT" "2.287593,20.398591,4.012028")
(COMMAND "POINT" "2.458594,20.276923,3.878166")
(COMMAND "POINT" "2.636978,20.146115,3.737859")
(COMMAND "POINT" "2.822744,20.006165,3.591108")
(COMMAND "POINT" "3.015891,19.857074,3.437912")
(COMMAND "POINT" "3.216421,19.698841,3.278271")
(COMMAND "POINT" "3.424333,19.531468,3.112185")
(COMMAND "POINT" "3.638216,19.356376,2.941023")
(COMMAND "POINT" "3.849609,19.182105,2.772993")
(COMMAND "POINT" "4.057099,19.010078,2.609464")
(COMMAND "POINT" "4.260687,18.840295,2.450435")
(COMMAND "POINT" "4.460374,18.672755,2.295906")
(COMMAND "POINT" "4.656159,18.507460,2.145877")
(COMMAND "POINT" "4.848042,18.344408,2.000349")
(COMMAND "POINT" "5.036023,18.183600,1.859322")
(COMMAND "POINT" "5.220102,18.025037,1.722795")
(COMMAND "POINT" "5.400280,17.868716,1.590768")
(COMMAND "POINT" "5.576556,17.714640,1.463241")
(COMMAND "POINT" "5.748930,17.562808,1.340215")
(COMMAND "POINT" "5.917402,17.413219,1.221689")
(COMMAND "POINT" "6.081972,17.265875,1.107664")
(COMMAND "POINT" "6.242640,17.120774,0.998139")
(COMMAND "POINT" "6.399407,16.977917,0.893114")
(COMMAND "POINT" "6.552272,16.837304,0.792590")
(COMMAND "POINT" "6.701235,16.698935,0.696566")
(COMMAND "POINT" "6.846296,16.562810,0.605043")
(COMMAND "POINT" "6.987455,16.428928,0.518020")
(COMMAND "POINT" "7.124713,16.297290,0.435497")
(COMMAND "POINT" "7.258069,16.167897,0.357474")
(COMMAND "POINT" "7.387523,16.040747,0.283952")
(COMMAND "POINT" "7.513075,15.915841,0.214931")
(COMMAND "POINT" "7.634725,15.793179,0.150410")
(COMMAND "POINT" "7.752473,15.672760,0.090389")
(COMMAND "POINT" "7.866320,15.554586,0.034868")
(COMMAND "POINT" "7.976265,15.438655,-0.016152")
(COMMAND "POINT" "8.082308,15.324969,-0.062672")
(COMMAND "POINT" "8.184449,15.213526,-0.104691")
(COMMAND "POINT" "8.282688,15.104327,-0.142210")
(COMMAND "POINT" "8.377026,14.997372,-0.175229")
(COMMAND "POINT" "8.467462,14.892660,-0.203747")
(COMMAND "POINT" "8.553996,14.790193,-0.227765")
(COMMAND "POINT" "8.636628,14.689969,-0.247282")
(COMMAND "POINT" "8.715358,14.591990,-0.262300")
(COMMAND "POINT" "8.790186,14.496254,-0.272816")
(COMMAND "POINT" "8.861113,14.402762,-0.278833")
(COMMAND "POINT" "8.928138,14.311514,-0.280349")
(COMMAND "POINT" "8.991261,14.222510,-0.277364")
(COMMAND "POINT" "9.050482,14.135749,-0.269880")
(COMMAND "POINT" "9.105801,14.051233,-0.257894")
(COMMAND "POINT" "9.157219,13.968960,-0.241409")
(COMMAND "POINT" "9.204734,13.888931,-0.220423")
(COMMAND "POINT" "9.248348,13.811146,-0.194937")
(COMMAND "POINT" "9.288060,13.735605,-0.164950")
(COMMAND "POINT" "9.323871,13.662308,-0.130463")
(COMMAND "POINT" "9.355779,13.591255,-0.091476")
(COMMAND "POINT" "9.383786,13.522445,-0.047988")
(COMMAND "POINT" "9.407891,13.455879,0.000000")
(COMMAND "POINT" "1.895945,17.035619,3.752921")
(COMMAND "POINT" "1.740502,17.314282,3.899361")
(COMMAND "POINT" "1.592651,17.583530,4.039214")
(COMMAND "POINT" "1.452393,17.843365,4.172478")
(COMMAND "POINT" "1.319726,18.093786,4.299155")
(COMMAND "POINT" "1.194652,18.334792,4.419245")
(COMMAND "POINT" "1.077169,18.566385,4.532746")
(COMMAND "POINT" "0.967279,18.788564,4.639660")
(COMMAND "POINT" "0.864981,19.001328,4.739986")
(COMMAND "POINT" "0.770274,19.204679,4.833724")
(COMMAND "POINT" "0.683160,19.398616,4.920874")
(COMMAND "POINT" "0.603638,19.583139,5.001437")
(COMMAND "POINT" "0.531707,19.758247,5.075412")
(COMMAND "POINT" "0.467369,19.923942,5.142799")
(COMMAND "POINT" "0.410623,20.080223,5.203598")
(COMMAND "POINT" "0.361469,20.227090,5.257810")
(COMMAND "POINT" "0.319907,20.364543,5.305433")
(COMMAND "POINT" "0.285937,20.492582,5.346469")
(COMMAND "POINT" "0.259559,20.611207,5.380918")
(COMMAND "POINT" "0.240773,20.720418,5.408778")
(COMMAND "POINT" "0.229579,20.820215,5.430051")
(COMMAND "POINT" "0.225977,20.910598,5.444736")
(COMMAND "POINT" "0.229967,20.991567,5.452833")
(COMMAND "POINT" "0.241550,21.063122,5.454342")
(COMMAND "POINT" "0.260724,21.125264,5.449264")
(COMMAND "POINT" "0.287490,21.177991,5.437597")
(COMMAND "POINT" "0.321848,21.221304,5.419343")
(COMMAND "POINT" "0.363799,21.255203,5.394502")
(COMMAND "POINT" "0.413341,21.279688,5.363072")
(COMMAND "POINT" "0.470476,21.294760,5.325055")
(COMMAND "POINT" "0.535202,21.300417,5.280450")
(COMMAND "POINT" "0.607521,21.296660,5.229257")
(COMMAND "POINT" "0.687431,21.283490,5.171476")
(COMMAND "POINT" "0.774934,21.260905,5.107108")
(COMMAND "POINT" "0.870029,21.228907,5.036152")
(COMMAND "POINT" "0.972715,21.187494,4.958608")
(COMMAND "POINT" "1.082994,21.136668,4.874476")
(COMMAND "POINT" "1.200865,21.076427,4.783757")
(COMMAND "POINT" "1.326328,21.006773,4.686450")
(COMMAND "POINT" "1.459382,20.927704,4.582555")
(COMMAND "POINT" "1.600029,20.839222,4.472072")
(COMMAND "POINT" "1.748268,20.741325,4.355001")
(COMMAND "POINT" "1.904099,20.634015,4.231343")
(COMMAND "POINT" "2.067522,20.517291,4.101097")
(COMMAND "POINT" "2.238537,20.391152,3.964263")
(COMMAND "POINT" "2.417144,20.255600,3.820841")
(COMMAND "POINT" "2.603343,20.110634,3.670832")
(COMMAND "POINT" "2.797135,19.956254,3.514235")
(COMMAND "POINT" "2.998518,19.792460,3.351050")
(COMMAND "POINT" "3.207493,19.619251,3.181277")
(COMMAND "POINT" "3.422607,19.438087,3.006315")
(COMMAND "POINT" "3.635143,19.257712,2.834555")
(COMMAND "POINT" "3.843646,19.079585,2.667395")
(COMMAND "POINT" "4.048118,18.903705,2.504835")
(COMMAND "POINT" "4.248558,18.730072,2.346876")
(COMMAND "POINT" "4.444967,18.558687,2.193517")
(COMMAND "POINT" "4.637343,18.389550,2.044758")
(COMMAND "POINT" "4.825688,18.222659,1.900600")
(COMMAND "POINT" "5.010001,18.058017,1.761041")
(COMMAND "POINT" "5.190282,17.895621,1.626083")
(COMMAND "POINT" "5.366531,17.735473,1.495726")
(COMMAND "POINT" "5.538748,17.577573,1.369968")
(COMMAND "POINT" "5.706934,17.421919,1.248811")
(COMMAND "POINT" "5.871088,17.268514,1.132255")
(COMMAND "POINT" "6.031210,17.117355,1.020298")
(COMMAND "POINT" "6.187300,16.968444,0.912942")
(COMMAND "POINT" "6.339359,16.821781,0.810186")
(COMMAND "POINT" "6.487385,16.677364,0.712030")
(COMMAND "POINT" "6.631380,16.535196,0.618475")
(COMMAND "POINT" "6.771343,16.395274,0.529520")
(COMMAND "POINT" "6.907274,16.257600,0.445165")
(COMMAND "POINT" "7.039174,16.122174,0.365410")
(COMMAND "POINT" "7.167041,15.988995,0.290256")
(COMMAND "POINT" "7.290877,15.858063,0.219702")
(COMMAND "POINT" "7.410681,15.729379,0.153749")
(COMMAND "POINT" "7.526454,15.602942,0.092395")
(COMMAND "POINT" "7.638194,15.478753,0.035642")
(COMMAND "POINT" "7.745903,15.356811,-0.016511")
(COMMAND "POINT" "7.849579,15.237116,-0.064063")
(COMMAND "POINT" "7.949224,15.119669,-0.107015")
(COMMAND "POINT" "8.044838,15.004469,-0.145367")
(COMMAND "POINT" "8.136419,14.891516,-0.179119")
(COMMAND "POINT" "8.223969,14.780811,-0.208270")
(COMMAND "POINT" "8.307486,14.672354,-0.232821")
(COMMAND "POINT" "8.386972,14.566144,-0.252772")
(COMMAND "POINT" "8.462427,14.462181,-0.268123")
(COMMAND "POINT" "8.533849,14.360466,-0.278873")
(COMMAND "POINT" "8.601240,14.260998,-0.285023")
(COMMAND "POINT" "8.664598,14.163777,-0.286573")
(COMMAND "POINT" "8.723925,14.068804,-0.283522")
(COMMAND "POINT" "8.779220,13.976078,-0.275871")
(COMMAND "POINT" "8.830484,13.885600,-0.263620")
(COMMAND "POINT" "8.877715,13.797369,-0.246768")
(COMMAND "POINT" "8.920915,13.711386,-0.225317")
(COMMAND "POINT" "8.960083,13.627649,-0.199265")
(COMMAND "POINT" "8.995219,13.546161,-0.168612")
(COMMAND "POINT" "9.026324,13.466920,-0.133360")
(COMMAND "POINT" "9.053396,13.389926,-0.093507")
(COMMAND "POINT" "9.076437,13.315179,-0.049053")
(COMMAND "POINT" "9.095446,13.242680,0.000000")
(COMMAND "POINT" "1.875318,17.087864,3.835181")
(COMMAND "POINT" "1.710684,17.373773,3.984832")
(COMMAND "POINT" "1.553854,17.649994,4.127750")
(COMMAND "POINT" "1.404829,17.916527,4.263935")
(COMMAND "POINT" "1.263609,18.173371,4.393389")
(COMMAND "POINT" "1.130193,18.420528,4.516111")
(COMMAND "POINT" "1.004583,18.657996,4.632100")
(COMMAND "POINT" "0.886777,18.885776,4.741357")
(COMMAND "POINT" "0.776777,19.103868,4.843882")
(COMMAND "POINT" "0.674581,19.312272,4.939675")
(COMMAND "POINT" "0.580190,19.510988,5.028736")
(COMMAND "POINT" "0.493603,19.700015,5.111064")
(COMMAND "POINT" "0.414822,19.879354,5.186660")
(COMMAND "POINT" "0.343845,20.049006,5.255524")
(COMMAND "POINT" "0.280674,20.208969,5.317656")
(COMMAND "POINT" "0.225307,20.359243,5.373056")
(COMMAND "POINT" "0.177745,20.499830,5.421724")
(COMMAND "POINT" "0.137987,20.630729,5.463659")
(COMMAND "POINT" "0.106035,20.751939,5.498863")
(COMMAND "POINT" "0.081887,20.863461,5.527334")
(COMMAND "POINT" "0.065545,20.965295,5.549073")
(COMMAND "POINT" "0.057007,21.057441,5.564079")
(COMMAND "POINT" "0.056274,21.139899,5.572354")
(COMMAND "POINT" "0.063346,21.212669,5.573896")
(COMMAND "POINT" "0.078222,21.275750,5.568707")
(COMMAND "POINT" "0.100904,21.329144,5.556785")
(COMMAND "POINT" "0.131390,21.372849,5.538131")
(COMMAND "POINT" "0.169681,21.406866,5.512744")
(COMMAND "POINT" "0.215777,21.431195,5.480626")
(COMMAND "POINT" "0.269678,21.445835,5.441775")
(COMMAND "POINT" "0.331384,21.450788,5.396193")
(COMMAND "POINT" "0.400895,21.446052,5.343878")
(COMMAND "POINT" "0.478210,21.431629,5.284831")
(COMMAND "POINT" "0.563330,21.407517,5.219051")
(COMMAND "POINT" "0.656255,21.373717,5.146540")
(COMMAND "POINT" "0.756985,21.330228,5.067296")
(COMMAND "POINT" "0.865520,21.277052,4.981321")
(COMMAND "POINT" "0.981859,21.214187,4.888613")
(COMMAND "POINT" "1.106004,21.141635,4.789172")
(COMMAND "POINT" "1.237953,21.059394,4.683000")
(COMMAND "POINT" "1.377707,20.967465,4.570096")
(COMMAND "POINT" "1.525266,20.865848,4.450459")
(COMMAND "POINT" "1.680630,20.754542,4.324090")
(COMMAND "POINT" "1.843799,20.633549,4.190989")
(COMMAND "POINT" "2.014772,20.502867,4.051156")
(COMMAND "POINT" "2.193550,20.362498,3.904591")
(COMMAND "POINT" "2.380134,20.212440,3.751293")
(COMMAND "POINT" "2.574522,20.052694,3.591264")
(COMMAND "POINT" "2.776714,19.883259,3.424502")
(COMMAND "POINT" "2.986712,19.704137,3.251008")
(COMMAND "POINT" "3.203018,19.516819,3.072211")
(COMMAND "POINT" "3.416656,19.330259,2.896686")
(COMMAND "POINT" "3.626129,19.145949,2.725862")
(COMMAND "POINT" "3.831438,18.963890,2.559739")
(COMMAND "POINT" "4.032582,18.784081,2.398317")
(COMMAND "POINT" "4.229561,18.606522,2.241597")
(COMMAND "POINT" "4.422375,18.431214,2.089577")
(COMMAND "POINT" "4.611025,18.258156,1.942259")
(COMMAND "POINT" "4.795510,18.087349,1.799642")
(COMMAND "POINT" "4.975831,17.918792,1.661726")
(COMMAND "POINT" "5.151987,17.752486,1.528511")
(COMMAND "POINT" "5.323978,17.588430,1.399997")
(COMMAND "POINT" "5.491804,17.426624,1.276184")
(COMMAND "POINT" "5.655466,17.267069,1.157073")
(COMMAND "POINT" "5.814963,17.109764,1.042662")
(COMMAND "POINT" "5.970295,16.954710,0.932953")
(COMMAND "POINT" "6.121463,16.801906,0.827944")
(COMMAND "POINT" "6.268466,16.651353,0.727637")
(COMMAND "POINT" "6.411305,16.503049,0.632031")
(COMMAND "POINT" "6.549978,16.356997,0.541126")
(COMMAND "POINT" "6.684487,16.213194,0.454923")
(COMMAND "POINT" "6.814832,16.071643,0.373420")
(COMMAND "POINT" "6.941012,15.932341,0.296618")
(COMMAND "POINT" "7.063027,15.795290,0.224518")
(COMMAND "POINT" "7.180877,15.660489,0.157119")
(COMMAND "POINT" "7.294563,15.527939,0.094421")
(COMMAND "POINT" "7.404084,15.397639,0.036423")
(COMMAND "POINT" "7.509440,15.269590,-0.016872")
(COMMAND "POINT" "7.610632,15.143791,-0.065467")
(COMMAND "POINT" "7.707659,15.020242,-0.109361")
(COMMAND "POINT" "7.800521,14.898944,-0.148554")
(COMMAND "POINT" "7.889219,14.779897,-0.183045")
(COMMAND "POINT" "7.973752,14.663099,-0.212835")
(COMMAND "POINT" "8.054120,14.548552,-0.237925")
(COMMAND "POINT" "8.130324,14.436256,-0.258313")
(COMMAND "POINT" "8.202363,14.326210,-0.274000")
(COMMAND "POINT" "8.270237,14.218414,-0.284986")
(COMMAND "POINT" "8.333947,14.112869,-0.291270")
(COMMAND "POINT" "8.393492,14.009574,-0.292854")
(COMMAND "POINT" "8.448872,13.908529,-0.289736")
(COMMAND "POINT" "8.500088,13.809735,-0.281918")
(COMMAND "POINT" "8.547139,13.713192,-0.269398")
(COMMAND "POINT" "8.590025,13.618899,-0.252177")
(COMMAND "POINT" "8.628746,13.526856,-0.230255")
(COMMAND "POINT" "8.663303,13.437063,-0.203632")
(COMMAND "POINT" "8.693696,13.349522,-0.172308")
(COMMAND "POINT" "8.719923,13.264230,-0.136283")
(COMMAND "POINT" "8.741986,13.181189,-0.095556")
(COMMAND "POINT" "8.759884,13.100398,-0.050129")
(COMMAND "POINT" "8.773618,13.021858,0.000000")
