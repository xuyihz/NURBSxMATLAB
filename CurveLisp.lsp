(COMMAND "POINT" "0.084642,0.063481")
(COMMAND "POINT" "0.182844,0.211055")
(COMMAND "POINT" "0.281219,0.350715")
(COMMAND "POINT" "0.379715,0.482585")
(COMMAND "POINT" "0.478279,0.606794")
(COMMAND "POINT" "0.576858,0.723465")
(COMMAND "POINT" "0.675399,0.832726")
(COMMAND "POINT" "0.773850,0.934702")
(COMMAND "POINT" "0.872158,1.029520")
(COMMAND "POINT" "0.970269,1.117305")
(COMMAND "POINT" "1.068132,1.198184")
(COMMAND "POINT" "1.165693,1.272281")
(COMMAND "POINT" "1.262900,1.339725")
(COMMAND "POINT" "1.359700,1.400639")
(COMMAND "POINT" "1.456040,1.455152")
(COMMAND "POINT" "1.551867,1.503387")
(COMMAND "POINT" "1.647129,1.545472")
(COMMAND "POINT" "1.741773,1.581532")
(COMMAND "POINT" "1.835746,1.611694")
(COMMAND "POINT" "1.928994,1.636083")
(COMMAND "POINT" "2.021467,1.654826")
(COMMAND "POINT" "2.113110,1.668048")
(COMMAND "POINT" "2.203871,1.675876")
(COMMAND "POINT" "2.293697,1.678435")
(COMMAND "POINT" "2.382535,1.675851")
(COMMAND "POINT" "2.470333,1.668251")
(COMMAND "POINT" "2.557038,1.655760")
(COMMAND "POINT" "2.642596,1.638505")
(COMMAND "POINT" "2.726956,1.616611")
(COMMAND "POINT" "2.810065,1.590205")
(COMMAND "POINT" "2.891869,1.559412")
(COMMAND "POINT" "2.972316,1.524359")
(COMMAND "POINT" "3.051353,1.485171")
(COMMAND "POINT" "3.128928,1.441975")
(COMMAND "POINT" "3.204987,1.394896")
(COMMAND "POINT" "3.279478,1.344061")
(COMMAND "POINT" "3.352348,1.289595")
(COMMAND "POINT" "3.423544,1.231624")
(COMMAND "POINT" "3.493013,1.170276")
(COMMAND "POINT" "3.560704,1.105674")
(COMMAND "POINT" "3.626562,1.037946")
(COMMAND "POINT" "3.690535,0.967218")
(COMMAND "POINT" "3.752571,0.893615")
(COMMAND "POINT" "3.812616,0.817264")
(COMMAND "POINT" "3.870619,0.738290")
(COMMAND "POINT" "3.926525,0.656820")
(COMMAND "POINT" "3.980282,0.572979")
(COMMAND "POINT" "4.031838,0.486894")
(COMMAND "POINT" "4.081140,0.398691")
(COMMAND "POINT" "4.128134,0.308495")
(COMMAND "POINT" "4.172769,0.216432")
(COMMAND "POINT" "4.214991,0.122629")
(COMMAND "POINT" "4.254748,0.027212")
(COMMAND "POINT" "4.291986,-0.069694")
(COMMAND "POINT" "4.326653,-0.167962")
(COMMAND "POINT" "4.358697,-0.267467")
(COMMAND "POINT" "4.388064,-0.368082")
(COMMAND "POINT" "4.414702,-0.469682")
(COMMAND "POINT" "4.438558,-0.572140")
(COMMAND "POINT" "4.459579,-0.675330")
(COMMAND "POINT" "4.477713,-0.779127")
(COMMAND "POINT" "4.492906,-0.883404")
(COMMAND "POINT" "4.505105,-0.988035")
(COMMAND "POINT" "4.514259,-1.092895")
(COMMAND "POINT" "4.520314,-1.197858")
(COMMAND "POINT" "4.523218,-1.302797")
(COMMAND "POINT" "4.522917,-1.407586")
(COMMAND "POINT" "4.519360,-1.512099")
(COMMAND "POINT" "4.512492,-1.616211")
(COMMAND "POINT" "4.502262,-1.719795")
(COMMAND "POINT" "4.488616,-1.822726")
(COMMAND "POINT" "4.471503,-1.924877")
(COMMAND "POINT" "4.450868,-2.026123")
(COMMAND "POINT" "4.426660,-2.126336")
(COMMAND "POINT" "4.398825,-2.225392")
(COMMAND "POINT" "4.367311,-2.323165")
(COMMAND "POINT" "4.332064,-2.419528")
(COMMAND "POINT" "4.293033,-2.514355")
(COMMAND "POINT" "4.250165,-2.607520")
(COMMAND "POINT" "4.203406,-2.698898")
(COMMAND "POINT" "4.152703,-2.788362")
(COMMAND "POINT" "4.098005,-2.875787")
(COMMAND "POINT" "4.039258,-2.961046")
(COMMAND "POINT" "3.976410,-3.044013")
(COMMAND "POINT" "3.909407,-3.124562")
(COMMAND "POINT" "3.838198,-3.202568")
(COMMAND "POINT" "3.762728,-3.277904")
(COMMAND "POINT" "3.682946,-3.350445")
(COMMAND "POINT" "3.598799,-3.420063")
(COMMAND "POINT" "3.510233,-3.486634")
(COMMAND "POINT" "3.417197,-3.550032")
(COMMAND "POINT" "3.319636,-3.610129")
(COMMAND "POINT" "3.217500,-3.666801")
(COMMAND "POINT" "3.110734,-3.719921")
(COMMAND "POINT" "2.999286,-3.769364")
(COMMAND "POINT" "2.883103,-3.815003")
(COMMAND "POINT" "2.762133,-3.856712")
(COMMAND "POINT" "2.636322,-3.894365")
(COMMAND "POINT" "2.505618,-3.927836")
(COMMAND "POINT" "2.369968,-3.957000")
